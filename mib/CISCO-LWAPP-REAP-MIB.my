-- *******************************************************************
-- CISCO-LWAPP-REAP-MIB.my
-- April 2007, Devesh Pujari, Prasanna Viswakumar, Srinath Candadai
--
-- Copyright (c) 2006-2007, 2013-2019 by Cisco Systems, Inc.
-- All rights reserved.
-- *******************************************************************
--
CISCO-LWAPP-REAP-MIB DEFINITIONS ::= BEGIN

IMPORTS
    MODULE-IDENTITY,
    OBJECT-TYPE,
    Unsigned32
        FROM SNMPv2-SMI
    MODULE-COMPLIANCE,
    OBJECT-GROUP
        FROM SNMPv2-CONF
    TruthValue,
    StorageType,
    RowStatus
        FROM SNMPv2-TC
    SnmpAdminString
        FROM SNMP-FRAMEWORK-MIB
    InetAddressType,
    InetAddress
    	FROM INET-ADDRESS-MIB
    cLWlanIndex
        FROM CISCO-LWAPP-WLAN-MIB
    cLApSysMacAddress
        FROM CISCO-LWAPP-AP-MIB
    ciscoMgmt
        FROM CISCO-SMI;


-- ********************************************************************
-- *  MODULE IDENTITY
-- ********************************************************************

ciscoLwappReapMIB MODULE-IDENTITY
    LAST-UPDATED    "201802260000Z"
    ORGANIZATION    "Cisco Systems Inc."
    CONTACT-INFO
            "Cisco Systems,
            Customer Service
            Postal: 170 West Tasman Drive
            San Jose, CA  95134 
	    USA
            Tel: +1 800 553-NETS

            Email: cs-wnbu-snmp@cisco.com"
    DESCRIPTION
        "This MIB is intended to be implemented on all those
        devices operating as Central Controllers (CC) that
        terminate the Light Weight Access Point Protocol
        tunnel from Light-weight LWAPP Access Points.

        Information represented by this MIB is passed by the
        controller to those Cisco LWAPP APs, that can
        operate in stand-alone mode.  

        The relationship between CC and the LWAPP APs
        can be depicted as follows:

        +......+     +......+     +......+           +......+
        +      +     +      +     +      +           +      +
        +  CC  +     +  CC  +     +  CC  +           +  CC  +
        +      +     +      +     +      +           +      +
        +......+     +......+     +......+           +......+
        ..            .             .                 .
        ..            .             .                 .
        .  .            .             .                 .
        .    .            .             .                 .
        .      .            .             .                 .
        .        .            .             .                 .
        +......+ +......+     +......+      +......+          +......+
        +      + +      +     +      +      +      +          +      +
        +  AP  + +  AP  +     +  AP  +      +  AP  +          +  AP  +
        +      + +      +     +      +      +      +          +      +
        +......+ +......+     +......+      +......+          +......+
        .              .             .                 .
        .  .              .             .                 .
        .    .              .             .                 .
        .      .              .             .                 .
        .        .              .             .                 .
        +......+ +......+     +......+      +......+          +......+
        +      + +      +     +      +      +      +          +      +
        +  MN  + +  MN  +     +  MN  +      +  MN  +          +  MN  +
        +      + +      +     +      +      +      +          +      +
        +......+ +......+     +......+      +......+          +......+


        The LWAPP tunnel exists between the controller and
        the APs.  The MNs communicate with the APs through
        the protocol defined by the 802.11 standard.

        LWAPP APs, upon bootup, discover and join one of the
        controllers and the controller pushes the configuration,
        that includes the WLAN parameters, to the LWAPP APs.
        The APs then encapsulate all the 802.11 frames from
        wireless clients inside LWAPP frames and forward
        the LWAPP frames to the controller.

                           GLOSSARY

        Access Point ( AP )

        An entity that contains an 802.11 medium access
        control ( MAC ) and physical layer ( PHY ) interface
        and provides access to the distribution services via
        the wireless medium for associated clients.  

        LWAPP APs encapsulate all the 802.11 frames in
        LWAPP frames and sends them to the controller to which
        it is logically connected.

        Central Controller ( CC )

        The central entity that terminates the LWAPP protocol
        tunnel from the LWAPP APs.  Throughout this MIB,
        this entity is also referred to as 'controller'.

        Light Weight Access Point Protocol ( LWAPP ) 

        This is a generic protocol that defines the
        communication between the Access Points and the
        Central Controller.

        Mobile Node ( MN )

        A roaming 802.11 wireless device in a wireless
        network associated with an access point.

        Native VLAN ID

        A switch port and/or AP can be configured with a
        'native VLAN ID'.  Untagged or priority-tagged
        frames are implicitly associated with the native
        VLAN ID.  The default native VLAN ID is '1' if
        VLAN tagging is enabled.  The native VLAN ID is '0'
        or 'no VLAN ID' if VLAN tagging is not enabled.

        Remote Edge Access Point ( REAP )

        The LWAPP AP that can also act as a stand-alone AP
        when it loses communication with the controller
        it was associated with.

        When REAP can reach the controller (connected state),
        it gets help from controller to complete client
        authentication. When a controller is not reachable by
        REAP, it goes into standalone state and does client
        authentication by itself.  All data packets from
        clients are either bridged locally (local-switch)
        or forwarded to the controller (central-switch)
        depending on the WLAN configuration.

        Virtual LAN

        VLAN defined in the IEEE 802.1Q VLAN standard
        supports logically segmenting of LAN
        infrastructure into different subnets or
        workgroups so that packets are switched only
        between ports within the same VLAN.

        VLAN ID
        Each VLAN is identified by a 12-bit 'VLAN ID'.
        A VLAN ID of '0' is used to indicate 'no VLAN ID'.
        Valid VLAN IDs range from '1' to '4095'. 

        Home AP 
        A REAP AP can be installed at end-user home. Home 
        AP ethernet port will be connected to DSL or cable
        modem at home. Home AP will be primed with Controller
        IP Address so that it will join with controller.

        REFERENCE

        [1] Part 11 Wireless LAN Medium Access Control ( MAC )
        and Physical Layer ( PHY ) Specifications 

        [2] Draft-obara-capwap-lwapp-00.txt, IETF Light 
        Weight Access Point Protocol"
    REVISION        "201808130000Z"
    DESCRIPTION
        "Added cLReapWlanPostAuthIpv4Acl and cLReapWlanPostAuthIpv6Acl in
        cLReapWlanConfigTable."
    REVISION        "201802260000Z"
    DESCRIPTION
        "Added cLReapAclUrlDomainRuleTable, cLReapIpv6AclTable,
        cLReapIpv6AclUrlDomainRuleTable, ciscoLwappReapMIBComplianceRev7,
  	ciscoLwappReapIpv6AclConfigGroup.	
	Deprecated ciscoLwappReapMIBComplianceRev6.
	Replaced ciscoLwappReapAclConfigGroup by ciscoLwappReapAclConfigGroupRev1."
    REVISION        "201704200000Z"
    DESCRIPTION
        "Added cLReapApVlanIdEntry, CLReapApVlanIdAclEntry,
        CLReapApWlanAclEntry, CLReapWebPolicyAclEntry,
        CLReapApLocalSplitACLEntry, CLReapApCentralDhcpEntry,
        CLReapApL2AclEntry, CLReapGroupVlanAclEntry,
        CLReapGroupAclEntry, CLReapGroupWebPolicyAclEntry"
    REVISION        "201010060000Z"
    DESCRIPTION
        "Added cLReapWlanApAuth, ciscoLwappReapWlanConfigGroupSup1,
        ciscoLwappReapMIBComplianceRev5.
        Deprecated ciscoLwappReapMIBComplianceRev4."
    REVISION        "201002060000Z"
    DESCRIPTION
        "Added cLReapWlanClientIpLearnEnable,
        cLReapHomeApEnable,cLReapApLeastLatencyJoinEnable
        and cLReapHomeApLocalSsidReset. Updated the description
        for cLReapGroupUserConfigTable,cLReapGroupUserName,
        and cLReapGroupPassword.
        In module identity's description removed EAP and added 
        Home AP.

        ciscoLwappReapMIBComplianceRev2 is deprecated. Added all 
        the groups which are in ciscoLwappReapMIBComplianceRev2 to 
        ciscoLwappReapMIBComplianceRev3. cLReapGroupRadiusPacTimeout
        is deprecated and created a new OID called
        cLReapGroupRadiusPacTimeoutCtrl. Created new group  
        ciscoLwappReapApConfigGroupHomeAp."
    REVISION        "200711010000Z"
    DESCRIPTION
        "Added  ciscoLwappReapGroupConfigRadiusGroup and
        ciscoLwappReapGroupConfigUserAuthGroup."
    REVISION        "200704190000Z"
    DESCRIPTION
        "Added  cLReapGroupConfigTable and
        cLReapGroupApConfigTable."
    REVISION        "200604190000Z"
    DESCRIPTION
        "Initial version of this MIB module."
    ::= { ciscoMgmt 517 }


ciscoLwappReapMIBNotifs  OBJECT IDENTIFIER
    ::= { ciscoLwappReapMIB 0 }

ciscoLwappReapMIBObjects  OBJECT IDENTIFIER
    ::= { ciscoLwappReapMIB 1 }

ciscoLwappReapMIBConform  OBJECT IDENTIFIER
    ::= { ciscoLwappReapMIB 2 }

ciscoLwappReapWlanConfig  OBJECT IDENTIFIER
    ::= { ciscoLwappReapMIBObjects 1 }

ciscoLwappReapApConfig  OBJECT IDENTIFIER
    ::= { ciscoLwappReapMIBObjects 2 }

ciscoLwappReapGroupConfig  OBJECT IDENTIFIER
    ::= { ciscoLwappReapMIBObjects 3 }

ciscoLwappReapAclConfig OBJECT IDENTIFIER
    ::= { ciscoLwappReapMIBObjects 4 }

ciscoLwappReapMasterApConfig OBJECT IDENTIFIER
    ::= { ciscoLwappReapMIBObjects 5 }

ciscoLwappReapGlobalConfig OBJECT IDENTIFIER
    ::= { ciscoLwappReapMIBObjects 6 }
    
ciscoLwappReapIpv6AclConfig OBJECT IDENTIFIER
    ::= { ciscoLwappReapMIBObjects 7 }
-- ********************************************************************
-- WLAN configuration
-- ********************************************************************

cLReapWlanConfigTable OBJECT-TYPE
    SYNTAX          SEQUENCE OF CLReapWlanConfigEntry 
    MAX-ACCESS      not-accessible
    STATUS          current
    DESCRIPTION
        "This table represents the WLAN configuration sent by
        the controller to REAPs so that the APs can operate
        in stand-alone mode.

        LWAPP APs operating in REAP mode locally switch 
        the data frames of the associated clients, rather 
        than tunneling them through to the LWAPP controller 
        as LWAPP data packets.  The LWAPP controller
        passes this configuration set to the LWAPP AP during
        the AP initialization so that the AP can operate
        in stand-alone mode when it fails to reach the
        controller.  The configuration is also passed to
        the REAP when they are individually modified through
        separate LWAPP messages.  The REAP updates itself
        with the information received through these LWAPP
        messages.

        This table has a one-to-one relationship with
        cLWlanConfigTable of the CISCO-LWAPP-WLAN-MIB.  There
        exist a row in this table corresponding to each
        row representing a WLAN in cLWlanConfigTable.

        Note that the configuration represented by this 
        table is applicable only for REAPs.  The 
        controller will send this configuration set only to 
        the REAP APs for their operation in standalone
        mode."
    ::= { ciscoLwappReapWlanConfig 1 }

cLReapWlanConfigEntry OBJECT-TYPE
    SYNTAX          CLReapWlanConfigEntry
    MAX-ACCESS      not-accessible
    STATUS          current
    DESCRIPTION
        "Each entry represents a conceptual row in
        cLReapWlanConfigTable and corresponds to the
        packet switching configuration for a
        particular WLAN."
--The following was converted from AUGMENTS to INDEX to separate
--implementation and does not have any external impact
--to users of MIB. The version available at mib-police page
--will be shipped to the customers. This version is for
--INTERNAL USE ONLY.
--    AUGMENTS { cLWlanConfigEntry }
    INDEX           { cLWlanIndex } 
    ::= { cLReapWlanConfigTable 1 }

CLReapWlanConfigEntry ::= SEQUENCE {
        cLReapWlanEnLocalSwitching    TruthValue,
        cLReapWlanClientIpLearnEnable TruthValue,
        cLReapWlanApAuth              TruthValue,
        cLReapWlanVlanCentralSwitching   TruthValue, 
        cLReapWlanDhcpCentral      TruthValue, 
        cLReapWlanDhcpOverrideDNS  TruthValue,
	cLReapWlanNatPatEnabled    TruthValue,
        cLReapWlanAssocCentral     TruthValue,
        cLReapWlanPostAuthIpv4Acl  SnmpAdminString,
        cLReapWlanPostAuthIpv6Acl  SnmpAdminString
}

cLReapWlanEnLocalSwitching OBJECT-TYPE
    SYNTAX          TruthValue
    MAX-ACCESS      read-write
    STATUS          current
    DESCRIPTION
        "This object specifies the behavior of the REAP
        when switching the data frames of the clients
        associated to it through the WLAN identified
        by cLWlanIndex.

        A value of 'true' indicates that the AP, on which 
        this WLAN is configured, may locally switch the 
        data packets of the clients in the WLAN instead
        of tunneling them to the central controller for
        switching.

        A value of 'false' indicates that the AP should 
        tunnel all the data packets of the wireless clients
        in the WLAN to the central controller for switching.

        Note that the value of 'true' will be effective
        only if the WLAN is configured on a REAP."
    DEFVAL          { false } 
    ::= { cLReapWlanConfigEntry 1 }

cLReapWlanClientIpLearnEnable OBJECT-TYPE
    SYNTAX          TruthValue
    MAX-ACCESS      read-write
    STATUS          current
    DESCRIPTION
        "This object specifies whether Client IP Address
        learning is enabled on the controller. When layer
        two tunneling is employed the IP learning on 
        controller has to be disabled. Otherwise, the controller
        is unable to learn the client's IP address and cannot 
        move it to the associated state. 
        A value of 'true' indicates the controller does checks
        for IP sent by the HREAP AP.
        A value of 'false' indicates the controller does
        not check for IP from the locally switch HREAP AP."
    DEFVAL          { true } 
    ::= { cLReapWlanConfigEntry 2 }

cLReapWlanApAuth OBJECT-TYPE
    SYNTAX          TruthValue
    MAX-ACCESS      read-write
    STATUS          current
    DESCRIPTION
        "This object specifies the behavior of the REAP,
        on where to handle the authentication of the client
        associated to the WLAN indicated by cLWlanIndex.

        A value of 'true' indicates that the AP, on which
        this WLAN is configured, will do the authentication
        of the clients in the WLAN locally at AP instead of
        of sending them to the central controller.

        A value of 'false' indicates that the AP should
        send the information to the central controller
        to do the authentication of the client.

        Note that the value of 'true' will be effective
        only if the WLAN is configured on a REAP AP and
        WLAN is configured for local switching of the data."
    DEFVAL          { false } 
    ::= { cLReapWlanConfigEntry 3 }

cLReapWlanVlanCentralSwitching OBJECT-TYPE
    SYNTAX     TruthValue
    MAX-ACCESS read-write
    STATUS     current
    DESCRIPTION
         "This object specifies whether the AP bridges the traffic 
         centrally. If the VLAN is not configured on the AP uplink,
	 the AP will tunnel the traffic back to the Wireless LAN 
	 Controller (WLC) where it is registered. Then the controller
	 will bridge the traffic into the corresponding VLAN from 
	 where it will be transported towards the next routing 
	 instance for further processing. 
	 
	 A value of 'true' indicates that the AP, should tunnel
	 traffic to WLC if VLAN not configured.
	 
	 A value of 'false' indicates that the AP, should bridge
	 traffic locally always.
	 
      	 This feature will be applicable only to locally switched WLANs."
    DEFVAL  { false }
	::= { cLReapWlanConfigEntry 4 }

cLReapWlanDhcpCentral OBJECT-TYPE
    SYNTAX     TruthValue
    MAX-ACCESS read-write
    STATUS     current
    DESCRIPTION
            "This object specifies the behavior of the REAP
            when switching the DHCP packets of the clients
            associated to it through the WLAN identified
            by cLWlanIndex.

	    A value of 'true' indicates that the AP, should tunnel
	    DHCP traffic to WLC.
	 
	    A value of 'false' indicates that the AP, should bridge
	    DHCP traffic locally always.
	 
            The value of 'true' will be effective
            only if the WLAN is configured on a REAP.
	    
	    This feature will be applicable only to locally 
	    switched WLANs."
    DEFVAL  { false }
    ::= { cLReapWlanConfigEntry 5 }

cLReapWlanDhcpOverrideDNS OBJECT-TYPE
    SYNTAX     TruthValue
    MAX-ACCESS read-write
    STATUS     current
    DESCRIPTION
            "This object specifies the behavior of the REAP
            when switching the DNS frames of the clients
            associated to it through the WLAN identified
            by cLWlanIndex.

	    A value of 'true' indicates that the AP, should tunnel
	    DNS traffic to WLC for DNS resolution.
	 
	    A value of 'false' indicates that the AP, should bridge
	    DNS traffic locally for DNS resolution.
	    
            The value of 'true' will be effective
            only if the WLAN is configured on a REAP.
	    
	    This feature will be applicable only to locally 
	    switched, central DHCP WLANs."
    DEFVAL  { false }
    ::= { cLReapWlanConfigEntry 6 }

cLReapWlanNatPatEnabled OBJECT-TYPE
    SYNTAX     TruthValue
    MAX-ACCESS read-write
    STATUS     current
    DESCRIPTION
            "This object specifies whether Network Address
	    Translation (NAT) and Port Address Trnaslation (PAT)
	    are enabled on this WLAN. This can be enabled only
	    when cLReapWlanDhcpCentral is set to 'true'.
	    
	    A value of 'true' indicates AP should bridge traffic
	    locally only after doing NAT and PAT.
	    
	    A value of 'false' indicates AP should bridge traffic
	    locally without doing NAT and PAT.
	    
            The value of 'true' will be effective
            only if the WLAN is configured as locally switched. "
    DEFVAL  { false }
    ::= { cLReapWlanConfigEntry 7 }

cLReapWlanAssocCentral OBJECT-TYPE
    SYNTAX     TruthValue
    MAX-ACCESS read-write
    STATUS     current
    DESCRIPTION
            "This object specifies the behavior of the REAP
            when handling the (re-)association management frames from
            the clients through the WLAN identified
            by cLWlanIndex.

	    A value of 'true' indicates AP should tunnel 
	    (re-) association management frames to WLC always.
	    
	    A value of 'false' indicates AP should process 
	    (re-) association management frames first and 
	    send the frame to WLC after appending association ID (AID)
	    to the frame.
	    
            The value of 'true' will be effective
            only if the WLAN is configured on a REAP. "
    DEFVAL  { false }
    ::= { cLReapWlanConfigEntry 8 } 

cLReapWlanPostAuthIpv4Acl OBJECT-TYPE
    SYNTAX     SnmpAdminString
    MAX-ACCESS read-write
    STATUS     current
    DESCRIPTION
            "This object specfies the Flexconnect IPv4 Post Auth ACL
            attached to the WLAN."

    ::= { cLReapWlanConfigEntry 9 } 

cLReapWlanPostAuthIpv6Acl OBJECT-TYPE
    SYNTAX     SnmpAdminString
    MAX-ACCESS read-write
    STATUS     current
    DESCRIPTION
            "This object specfies the Flexconnect IPv6 Post Auth ACL
            attached to the WLAN."

    ::= { cLReapWlanConfigEntry 10 }

-- ********************************************************************
-- *    Cisco REAP AP Configuration
-- ********************************************************************

cLReapApConfigTable OBJECT-TYPE
    SYNTAX          SEQUENCE OF CLReapApConfigEntry 
    MAX-ACCESS      not-accessible
    STATUS          current
    DESCRIPTION
        "This table represents the VLAN configuration of
        REAPs.

        The agent adds a row to this table corresponding to
        each row representing a REAP in cLApTable of the
        CISCO-LWAPP-AP-MIB.  The agent deletes the row
        either when the AP dissociates from the
        controller or moved out of the remote mode."
    ::= { ciscoLwappReapApConfig 1 }

cLReapApConfigEntry OBJECT-TYPE
    SYNTAX          CLReapApConfigEntry
    MAX-ACCESS      not-accessible
    STATUS          current
    DESCRIPTION
        "Each entry represents a conceptual row in
        cLReapApConfigTable and corresponds to the
        VLAN configuration of a REAP."
    INDEX           { cLApSysMacAddress } 
    ::= { cLReapApConfigTable 1 }

CLReapApConfigEntry ::= SEQUENCE {
        cLReapApNativeVlanId           Unsigned32,
        cLReapApVlanEnable             TruthValue,
        cLReapHomeApEnable             TruthValue,
        cLReapApLeastLatencyJoinEnable TruthValue,
        cLReapHomeApLocalSsidReset     TruthValue,
        cLReapInstallMappingRadioBackhaul TruthValue,
        cLReapApResilientMode 	       TruthValue,
        cLReapApNativeVlanLevel        TruthValue
}

cLReapApNativeVlanId OBJECT-TYPE
    SYNTAX          Unsigned32 (1..4095)
    MAX-ACCESS      read-write
    STATUS          current
    DESCRIPTION
        "This object specifies the Native VLAN ID for the
        particular AP identified by cLApSysMacAddress.
        This particular object can be modified 
        through a Set request only if the AP is a REAP.
        The agent is expected to reject the attempt to set
        this object for APs in other modes.
	
	This can be set only when cLReapApVlanEnable
	is set to 'true' and AP mode is REAP"
    DEFVAL          { 1 } 
    ::= { cLReapApConfigEntry 1 }

cLReapApVlanEnable OBJECT-TYPE
    SYNTAX          TruthValue
    MAX-ACCESS      read-write
    STATUS          current
    DESCRIPTION
        "This object specifies the availability of Native
        VLAN configured through cLReapApNativeVlanId on
        this REAP.

        A value of 'true' indicates that the VLAN configured
        as native through cLReapApNativeVlanId is enabled
        on the REAP and that the REAP can reach the
        controller through the native VLAN.

        A value of 'false' indicates that the VLAN configured
        as native through cLReapApNativeVlanId is disabled
        and the REAP can reach the controller through AP 
	management VLAN."
    DEFVAL          { false } 
    ::= { cLReapApConfigEntry 2 }

cLReapHomeApEnable OBJECT-TYPE
    SYNTAX          TruthValue
    MAX-ACCESS      read-write
    STATUS          current
    DESCRIPTION
        "This object specifies if this REAP AP is used
        as Home AP. 

        A value of 'true' indicates that this REAP AP is 
        a Home AP.

        A value of 'false' indicates that this REAP AP is 
        not a Home AP."
    DEFVAL          { false } 
    ::= { cLReapApConfigEntry 3 }

cLReapApLeastLatencyJoinEnable OBJECT-TYPE
    SYNTAX          TruthValue
    MAX-ACCESS      read-write
    STATUS          current
    DESCRIPTION
        "This object specifies if this REAP AP should join
        controller which has least latency.

        A value of 'true' indicates that this REAP AP will
        join controller which has least latency.

        A value of 'false' indicates that this REAP AP will
        not consider latency in selecting controller to 
        join."
    DEFVAL          { false } 
    ::= { cLReapApConfigEntry 4 }

cLReapHomeApLocalSsidReset OBJECT-TYPE
    SYNTAX          TruthValue
    MAX-ACCESS      read-write
    STATUS          current
    DESCRIPTION
        "This object specifies to reset local SSID on a
        Home AP.
        A value of 'true' indicates that the local SSID 
        is to be reset.
        A value of 'false' on this during set will return 
        error.
        A value of false will be returned on get."
    DEFVAL          { false } 
    ::= { cLReapApConfigEntry 5 }
 
cLReapInstallMappingRadioBackhaul OBJECT-TYPE
         SYNTAX     TruthValue
         MAX-ACCESS read-write
         STATUS     current
         DESCRIPTION
                 "This object specifies whether to enable or disable
		  WLANs on backhaul radio.
		  
                  A value of 'true' indicates that wlan mapping would
                  be enabled on backhaul radio.
		  
                  A value of 'false' indicates that wlan mapping would
                  be disabled on backhaul radio.
		  
                  This value is applicable only when AP is in 
                  flex+bridge mode."
         DEFVAL  { false }
         ::= { cLReapApConfigEntry 6}

cLReapApResilientMode OBJECT-TYPE
         SYNTAX     TruthValue
         MAX-ACCESS read-write
         STATUS     current
         DESCRIPTION
                 "This object specifies whether to enable or disable 
                  standalone mode support on a REAP AP.
                  
		  A value of 'true' indicates that standalone mode would
                  be enabled on backhaul radio.
                  
		  A value of 'false' indicates that standalone mode  would
                  be disabled on backhaul radio.
                  
		  This variable is significant only when AP is in 
                  flex+bridge mode."
         DEFVAL  { false }
         ::= { cLReapApConfigEntry 7}

cLReapApNativeVlanLevel OBJECT-TYPE
         SYNTAX     TruthValue
         MAX-ACCESS read-write
         STATUS     current
         DESCRIPTION
                 "This object specifies to make a REAP AP to force 
                 inherit the vlan support and native vlan from the 
                 REAP group.
                  
                 A value of 'true' indicates that the AP should inherit
                 the vlan support and native vlan from the REAP
                 group to which it is connected.
		  
                 A value of 'false' indicates that the native vlan is
                 not inherited from the REAP group."
         DEFVAL  { false }
         ::= { cLReapApConfigEntry 8}

-- ********************************************************************
-- *    Cisco REAP WLAN / VLAN Id mapping configuration
-- ********************************************************************

cLReapApVlanIdTable OBJECT-TYPE
    SYNTAX          SEQUENCE OF CLReapApVlanIdEntry 
    MAX-ACCESS      not-accessible
    STATUS          current
    DESCRIPTION
        "This table represents the WLAN / VLAN Id mappings to be
        configured for the REAP identified by
        cLApSysMacAddress.

        VLAN Id configured through this table is passed to
        the respective REAP through the 'Add WLAN' LWAPP
        message, sent as part of the 'Configure Response
        message from the controller to the REAP, during
        the initialization of the REAP. The REAP maps
        the VLAN to the particular WLAN to locally switch
        the data packets when those APs are in standalone
        mode.  Thus, the information added through this
        table is applicable for REAPs only.

        VLANs are configured on WLANs for which local
        switching of packets is enabled through
        cLReapWlanEnLocalSwitching.  This means that
        a row is added to this table only if there
        are WLANs available on the controller with
        local switching enabled and the AP is a REAP."
    ::= { ciscoLwappReapApConfig 2 }

cLReapApVlanIdEntry OBJECT-TYPE
    SYNTAX          CLReapApVlanIdEntry
    MAX-ACCESS      not-accessible
    STATUS          current
    DESCRIPTION
        "Each entry represents a conceptual row that
        corresponds to one WLAN / VLAN Id mapping to 
        be applied to the REAP identified by
        cLApSysMacAddress."
    INDEX   { cLApSysMacAddress, cLWlanIndex } 
    ::= { cLReapApVlanIdTable 1 }

CLReapApVlanIdEntry ::= 
	SEQUENCE {
        cLReapApVlanId Unsigned32,
        cLReapApVlanInheritance  INTEGER,
        cLReapApVlanRowStatus RowStatus,
        cLReapApVlanUsedBySecEthInterface  TruthValue
        
	}

cLReapApVlanId OBJECT-TYPE
    SYNTAX          Unsigned32 (1..4095)
    MAX-ACCESS      read-create
    STATUS          current
    DESCRIPTION
        "This object specifies the VLAN ID to be mapped
        to the WLAN identified by cLWlanIndex."
    DEFVAL          { 1 } 
    ::= { cLReapApVlanIdEntry 1 }
 
cLReapApVlanInheritance OBJECT-TYPE
        SYNTAX     INTEGER  {
                   ap (1),
                   hreapGroup(2),
                   wlan (3)
        }
        MAX-ACCESS read-create
        STATUS     current
        DESCRIPTION
                "This object specifies the inheritance to be mapped
                to the WLAN identified by cLWlanIndex.
		
		A value of 'ap' specifies VLAN for that WLAN is 
		inherited from AP spcific configuration
		
		A value of 'hreapGroup' specifies VLAN for that WLAN is 
		inherited from hreap group configuration
		 
		A value of 'wlan' specifies VLAN for that WLAN is 
		inherited from WLAN or ap group configuration."
		
        DEFVAL  { ap }
        ::= { cLReapApVlanIdEntry  2 }

cLReapApVlanRowStatus OBJECT-TYPE
        SYNTAX     RowStatus 
        MAX-ACCESS read-create
        STATUS     current
        DESCRIPTION
                "This object specifies the rowstatus of the
                wlan vlan mappings table"
        ::= { cLReapApVlanIdEntry  3 }

cLReapApVlanUsedBySecEthInterface OBJECT-TYPE
        SYNTAX     TruthValue
        MAX-ACCESS read-only
        STATUS     current
        DESCRIPTION
                "This object indicates if vlan represented by 
                 cLReapApVlanId is used by any of the secondary
                 ethernet interface when the REAP AP is in 
                 flex+bridge mode.
		 
		 A value of 'true' indicates cLReapApVlanId is
		 used by secondary ethernet interface. 
		 
		 A value of 'false' indicates cLReapApVlanId is
		 not used by secondary ethernet interface."
		 
        DEFVAL  { false }
        ::= { cLReapApVlanIdEntry  4 }

-- *******************************************************************
--  Cisco REAP VLAN Id . ACL  mapping configuration on AP level
-- *******************************************************************

cLReapApVlanIdAclTable OBJECT-TYPE 
        SYNTAX     SEQUENCE OF CLReapApVlanIdAclEntry 
        MAX-ACCESS not-accessible 
        STATUS     current 
        DESCRIPTION 
                "This table represents the VLAN Id- ACL mappings to be 
                configured for the REAP identified by 
                cLApSysMacAddress." 
        ::= { ciscoLwappReapApConfig 3 }
	
cLReapApVlanIdAclEntry OBJECT-TYPE 
        SYNTAX     CLReapApVlanIdAclEntry 
        MAX-ACCESS not-accessible 
        STATUS     current 
        DESCRIPTION
                "Each entry represents a conceptual row that 
                corresponds to one VLAN Id - ACL mapping to 
                be applied to the REAP identified by 
                cLApSysMacAddress. " 
        INDEX   { cLApSysMacAddress, cLReapVlanId } 
        ::= { cLReapApVlanIdAclTable 1 } 
	
CLReapApVlanIdAclEntry ::= 
        SEQUENCE { 
                   cLReapVlanId      Unsigned32, 
                   cLReapIngressAcl  SnmpAdminString, 
                   cLReapEgressAcl   SnmpAdminString, 
                   cLReapApVlanIdAclRowStatus RowStatus, 
                   cLReapVlanIdAclType INTEGER
        }
	        
cLReapVlanId OBJECT-TYPE 
        SYNTAX     Unsigned32 (1..4095) 
        MAX-ACCESS not-accessible 
        STATUS     current 
        DESCRIPTION 
                "This object represents the VLAN ID to be mapped 
                to the ACL for the access point identified by 
                cLApSysMacAddress.  " 
        ::= { cLReapApVlanIdAclEntry  1 } 

cLReapIngressAcl OBJECT-TYPE 
      SYNTAX     SnmpAdminString (SIZE(0..32)) 
      MAX-ACCESS read-create 
      STATUS     current 
      DESCRIPTION 
             "This object specifies the name of the ingress Access
              Control List for the vlan-acl mapping."
        ::= { cLReapApVlanIdAclEntry  2 } 

cLReapEgressAcl OBJECT-TYPE
      SYNTAX     SnmpAdminString (SIZE(0..32))
      MAX-ACCESS read-create
      STATUS     current
      DESCRIPTION
             "This object specifies the name of the egress
              Access Control List for the vlan-acl mapping."
        ::= { cLReapApVlanIdAclEntry  3 } 

cLReapApVlanIdAclRowStatus OBJECT-TYPE 
        SYNTAX     RowStatus 
        MAX-ACCESS read-create 
        STATUS     current 
        DESCRIPTION 
                "This object specifies the status column for a 
                 conceptual row in this table." 
        ::= { cLReapApVlanIdAclEntry 4} 

cLReapVlanIdAclType OBJECT-TYPE
        SYNTAX          INTEGER  {
                        apSource(1),
                        groupSource(2)
                    }
        MAX-ACCESS read-only 
        STATUS     current
        DESCRIPTION
                "This object represents the type of the vlan acl mapping 
                 
		 A value of 'apSource' indicates that vlan-acl mapping 
		 applied from AP level.
                 
		 A value of 'groupSource' indicates that vlan-acl mapping
		 applied from hreap group level. "
        ::= { cLReapApVlanIdAclEntry  5 }

cLReapApWlanAclTable OBJECT-TYPE
        SYNTAX     SEQUENCE OF CLReapApWlanAclEntry
        MAX-ACCESS not-accessible  
        STATUS     current
        DESCRIPTION
                "This table represents the WLAN ACL mappings to be
                configured for the REAP identified by
                cLApSysMacAddress.
                A row is added to this table only if there
                are WLANs available on the controller with
                local switching enabled and the AP is a REAP. "
        ::= { ciscoLwappReapApConfig 4 }
       
cLReapApWlanAclEntry OBJECT-TYPE
        SYNTAX     CLReapApWlanAclEntry
        MAX-ACCESS not-accessible  
        STATUS     current
        DESCRIPTION
                "Each entry represents a conceptual row that
                corresponds to one WLAN / ACL mapping to 
                be applied to the REAP identified by
                cLApSysMacAddress. "
        INDEX   { cLApSysMacAddress, cLWlanIndex }
        ::= { cLReapApWlanAclTable 1 }
        
CLReapApWlanAclEntry ::=
        SEQUENCE {
                cLReapApWebAuthAcl           SnmpAdminString,
                cLReapApWebAuthAclRowStatus  RowStatus
        }

cLReapApWebAuthAcl OBJECT-TYPE
        SYNTAX     SnmpAdminString (SIZE(0..32))
        MAX-ACCESS read-create
        STATUS     current
        DESCRIPTION
                "This object specifies the webauth ACL name to be 
                mapped to the WLAN identified by cLWlanIndex.
		
		This will be applied to REAP AP only when
		webauth client associates to REAP AP." 
        ::= { cLReapApWlanAclEntry  1 }

cLReapApWebAuthAclRowStatus OBJECT-TYPE
        SYNTAX     RowStatus
        MAX-ACCESS read-create
        STATUS     current
        DESCRIPTION
                "This object specifies the status column for a
                 conceptual row in this table."
        ::= { cLReapApWlanAclEntry  2}


cLReapWebPolicyAclTable OBJECT-TYPE
        SYNTAX     SEQUENCE OF CLReapWebPolicyAclEntry
        MAX-ACCESS not-accessible
        STATUS     current
        DESCRIPTION
                "This table represents the web policies associated with
                 an AP. Entries are added or deleted by the user
                 through the use of cLReapWebPolicyRowStatus."
        ::= { ciscoLwappReapApConfig 5 }

cLReapWebPolicyAclEntry OBJECT-TYPE
        SYNTAX     CLReapWebPolicyAclEntry
        MAX-ACCESS not-accessible
        STATUS     current
        DESCRIPTION
                "Each entry represents a conceptual row in
                cLReapWebPolicyAclTable."
        INDEX   {cLApSysMacAddress,  cLReapWebPolicyAcl}
        ::= { cLReapWebPolicyAclTable 1 }

CLReapWebPolicyAclEntry ::=
        SEQUENCE {
                cLReapWebPolicyAcl           SnmpAdminString,
                cLReapWebPolicyAclRowStatus  RowStatus
        }

cLReapWebPolicyAcl OBJECT-TYPE
      SYNTAX     SnmpAdminString (SIZE(0..32))
      MAX-ACCESS not-accessible
      STATUS     current
      DESCRIPTION
             "This object represents the name of the web policy
              ACL to be mapped to the access point identified 
	      by cLApSysMacAddress."
        ::= { cLReapWebPolicyAclEntry  1 }

cLReapWebPolicyAclRowStatus OBJECT-TYPE
        SYNTAX     RowStatus
        MAX-ACCESS read-create
        STATUS     current
        DESCRIPTION
                "This object specifies the status column for a
                 conceptual row in this table."
        ::= { cLReapWebPolicyAclEntry  2}

cLReapApLocalSplitACLTable OBJECT-TYPE
        SYNTAX     SEQUENCE OF CLReapApLocalSplitACLEntry
        MAX-ACCESS not-accessible
        STATUS     current
        DESCRIPTION
                "This table represents the WLAN - local split ACL 
		mappings to be configured for the REAP AP 
		identified by cLApSysMacAddress."
        ::= { ciscoLwappReapApConfig 6 }

cLReapApLocalSplitACLEntry OBJECT-TYPE
        SYNTAX     CLReapApLocalSplitACLEntry
        MAX-ACCESS not-accessible
        STATUS     current
        DESCRIPTION
                "Each entry represents a conceptual row that
                corresponds to one WLAN- local split ACL mapping
		to be applied to the REAP identified by
                cLApSysMacAddress. "
        INDEX   { cLApSysMacAddress, cLWlanIndex }
        ::= { cLReapApLocalSplitACLTable 1 }

CLReapApLocalSplitACLEntry ::=
        SEQUENCE {
                cLReapApLocalSplitAcl      SnmpAdminString,
                cLReapApLocalSplitAclRowStatus RowStatus
        }

cLReapApLocalSplitAcl OBJECT-TYPE
        SYNTAX     SnmpAdminString (SIZE(0..32))
        MAX-ACCESS read-create
        STATUS     current
        DESCRIPTION
                "This object specifies the local split ACL name to be
                mapped to the WLAN identified by cLWlanIndex. 
		
		This is applicable only for central switching WLANs on 
		REAP AP"
        ::= { cLReapApLocalSplitACLEntry  1 }

cLReapApLocalSplitAclRowStatus OBJECT-TYPE
        SYNTAX     RowStatus
        MAX-ACCESS read-create
        STATUS     current
        DESCRIPTION
                "This object specifies the status column for a
                 conceptual row in this table."
        ::= { cLReapApLocalSplitACLEntry  2}


 --********************************************************************
 --*    Cisco REAP Central DHCP configuration
 --*********************************************************************
cLReapApCentralDhcpTable OBJECT-TYPE
        SYNTAX     SEQUENCE OF CLReapApCentralDhcpEntry
        MAX-ACCESS not-accessible
        STATUS     current
        DESCRIPTION
            "This object represents the behavior of the REAP
            AP when switching the DHCP packets of the clients
            associated to it through the WLAN identified
            by cLWlanIndex."
        ::= { ciscoLwappReapApConfig 7 }

cLReapApCentralDhcpEntry OBJECT-TYPE
        SYNTAX     CLReapApCentralDhcpEntry
        MAX-ACCESS not-accessible
        STATUS     current
        DESCRIPTION
           "This object represents the behavior of the REAP
            AP when switching the DHCP packets of the clients
            associated to it through the WLAN identified
            by cLWlanIndex."
        INDEX   { cLApSysMacAddress, cLWlanIndex }
        ::= { cLReapApCentralDhcpTable 1 }

CLReapApCentralDhcpEntry ::=
        SEQUENCE {
                cLReapApDhcpCentral      TruthValue,
                cLReapApDhcpOverrideDNS  TruthValue,
                cLReapApNatPatEnabled    TruthValue,
                cLReapApDhcpRowStatus RowStatus,
                cLReapApInheritance    SnmpAdminString

        }
cLReapApDhcpCentral OBJECT-TYPE
    SYNTAX     TruthValue
    MAX-ACCESS read-create
    STATUS     current
    DESCRIPTION
            "This object specifies the behavior of the REAP AP
            when switching the DHCP frames of the clients
            associated to it through the WLAN identified
            by cLWlanIndex.
	    
	    A value of 'true' specifies REAP AP will tunnel
	    DHCP packets to WLC.
	    
	    A value of 'false' specifies REAP AP will bridge
	    DHCP packets locally.
	    
	    This config is applicable only for locally
	    switched WLANs"
    DEFVAL  { false }
    ::= { cLReapApCentralDhcpEntry 1 }
    
cLReapApDhcpOverrideDNS OBJECT-TYPE
    SYNTAX     TruthValue
    MAX-ACCESS read-create
    STATUS     current
    DESCRIPTION
            "This object specifies the behavior of the REAP AP
            when switching the DNS frames of the clients
            associated to it through the WLAN identified
            by cLWlanIndex.
	    
	    A value of 'true' specifies REAP AP will tunnel
	    DNS packets to WLC.
	    
	    A value of 'false' specifies REAP AP will bridge
	    DNS packets locally.
	    
	    This config is applicable only for locally
	    switched WLANs and when cLReapApDhcpCentral is set to
	    'true'. "
    DEFVAL  { false }
    ::= { cLReapApCentralDhcpEntry 2 }
    
cLReapApNatPatEnabled OBJECT-TYPE
    SYNTAX     TruthValue
    MAX-ACCESS read-create
    STATUS     current
    DESCRIPTION
            "This object specifies whether Network Address
            Translation (NAT) and Port Address Trnaslation (PAT)
            are enabled on this REAP AP for the WLAN identified
            by cLWlanIndex.
	    
	    A value of 'true' specifies REAP AP will bridge data
	    packets locally after appliying NAT and PAT.
	    
	    A value of 'false' specifies REAP AP will bridge data
	    packets locally without appliying NAT and PAT.
	    
	    This config is applicable only for locally
	    switched WLANs and when cLReapApDhcpCentral is set to
	    'true'. "
    DEFVAL  { false }
    ::= { cLReapApCentralDhcpEntry 3 }


cLReapApDhcpRowStatus OBJECT-TYPE
        SYNTAX     RowStatus
        MAX-ACCESS read-create
        STATUS     current
        DESCRIPTION
                "This object represents the status column for a
                conceptual row in this table."
        ::= { cLReapApCentralDhcpEntry 4 }


cLReapApInheritance OBJECT-TYPE
        SYNTAX     SnmpAdminString 
        MAX-ACCESS read-only
        STATUS     current
        DESCRIPTION
                "This object represents the inheritance level 
                of central DHCP configuration. It can be inherted
		from AP or REAP group or WLAN configuration"
        ::= { cLReapApCentralDhcpEntry 5 }

--********************************************************************
--*    FlexConnect AP specific L2ACL configuration
--*********************************************************************
cLReapApL2AclTable OBJECT-TYPE
        SYNTAX     SEQUENCE OF CLReapApL2AclEntry
        MAX-ACCESS not-accessible  
        STATUS     current
        DESCRIPTION
                "This table represents the L2 ACL mappings to be
                configured for the REAP AP identified by
                cLApSysMacAddress.
                A row is added to this table only if there
                are WLANs available on the controller with
                local switching enabled and the AP is a REAP. "
        ::= { ciscoLwappReapApConfig 8 }
 
cLReapApL2AclEntry OBJECT-TYPE
        SYNTAX     CLReapApL2AclEntry
        MAX-ACCESS not-accessible  
        STATUS     current
        DESCRIPTION
                "Each entry represents a conceptual row that
                corresponds to one WLAN / L2 ACL mapping to 
                be applied to the REAP identified by
                cLApSysMacAddress. "
        INDEX   { cLApSysMacAddress, cLWlanIndex }
        ::= { cLReapApL2AclTable 1 }

CLReapApL2AclEntry ::=
        SEQUENCE {
                cLReapApL2Acl           SnmpAdminString,
                cLReapApL2AclRowStatus  RowStatus
        }

cLReapApL2Acl OBJECT-TYPE
        SYNTAX     SnmpAdminString (SIZE(0..32))
        MAX-ACCESS read-create
        STATUS     current
        DESCRIPTION
                "This object specifies the L2ACL name to be 
                mapped to the WLAN identified by cLWlanIndex 
                for this REAP AP " 
        ::= { cLReapApL2AclEntry  1 }

cLReapApL2AclRowStatus OBJECT-TYPE
        SYNTAX     RowStatus
        MAX-ACCESS read-create
        STATUS     current
        DESCRIPTION
                "This object specifies the status column for a
                 conceptual row in this table."
        ::= { cLReapApL2AclEntry  2}

-- ********************************************************************
-- Hybrid REAP Group configuration
-- ********************************************************************

cLReapGroupConfigTable OBJECT-TYPE
    SYNTAX          SEQUENCE OF CLReapGroupConfigEntry 
    MAX-ACCESS      not-accessible
    STATUS          current
    DESCRIPTION
        "This table represents the configuration for
        REAPs so that the APs can be configured as a 
        group.
        Entries are added or deleted by the user through
        the use of cLReapGroupRowStatus."
    ::= { ciscoLwappReapGroupConfig 1 }

cLReapGroupConfigEntry OBJECT-TYPE
    SYNTAX          CLReapGroupConfigEntry
    MAX-ACCESS      not-accessible
    STATUS          current
    DESCRIPTION
        "Each entry represents a conceptual row in
        cLReapGroupConfigTable."
    INDEX           { cLReapGroupName } 
    ::= { cLReapGroupConfigTable 1 }

CLReapGroupConfigEntry ::= SEQUENCE {
        cLReapGroupName                 SnmpAdminString,
        cLReapGroupPrimaryRadiusIndex   Unsigned32,
        cLReapGroupSecondaryRadiusIndex Unsigned32,
        cLReapGroupStorageType          StorageType,
        cLReapGroupRowStatus            RowStatus,
	cLReapGroupRadiusPacTimeout     Unsigned32,
        cLReapGroupRadiusAuthorityId    OCTET STRING,
        cLReapGroupRadiusAuthorityInfo  OCTET STRING,
        cLReapGroupRadiusServerKey      OCTET STRING,
        cLReapGroupRadiusIgnoreKey      TruthValue,
        cLReapGroupRadiusEnable         TruthValue,
        cLReapGroupRadiusLeapEnable     TruthValue,
        cLReapGroupRadiusEapFastEnable  TruthValue,
        cLReapGroupRadiusPacTimeoutCtrl Unsigned32,
        cLReapGroupEfficientApUpgradeEnable    TruthValue,
        cLReapGroupApUpgradeStart              INTEGER,
        cLReapGroupSlaveMaxRetryCount          Unsigned32,
        cLReapGroupPrimaryRadiusServerType     InetAddressType,
        cLReapGroupPrimaryRadiusServerAddress  InetAddress,
        cLReapGroupPrimaryRadiusServerPort     Unsigned32,
        cLReapGroupPrimaryServerSecret         SnmpAdminString, 
        cLReapGroupSecRadiusServerType     InetAddressType,
        cLReapGroupSecRadiusServerAddress  InetAddress,
        cLReapGroupSecRadiusServerPort     Unsigned32,
        cLReapGroupSecServerSecret         SnmpAdminString,
        cLReapGroupRadiusPeapEnable       TruthValue,
        cLReapGroupRadiusEapTlsEnable     TruthValue,
        cLReapGroupCertificateEapTlsEnable  TruthValue,
        cLReapGroupNativeVlanId    	    Unsigned32,
        cLReapGroupVlanEnable      	    TruthValue,
        cLReapGroupOverrideVlanEnable       TruthValue,
        cLReapGroupHttpProxyIpType          InetAddressType,
        cLReapGroupHttpProxyIp              InetAddress,
        cLReapGroupHttpProxyPort            Unsigned32,
        cLReapGroupVlanTemplateName       SnmpAdminString,
	cLReapGroupEfficientApJoinEnable    TruthValue,
        cLReapGroupAutoApTypeConversion  TruthValue
}

cLReapGroupName OBJECT-TYPE
    SYNTAX          SnmpAdminString
    MAX-ACCESS      not-accessible
    STATUS          current
    DESCRIPTION
        "This object represents REAP group name and 
	uniquely identifies an entry in cLReapGroupConfigTable." 
    ::= { cLReapGroupConfigEntry 1 }

cLReapGroupPrimaryRadiusIndex OBJECT-TYPE
    SYNTAX          Unsigned32
    MAX-ACCESS      read-create
    STATUS          current
    DESCRIPTION
        "The object specifies the value that maps to the
        primary RADIUS server for this group. 
	
	A value of '0' indicates that the primary RADIUS 
	server is not configured for this group."
    DEFVAL          { 0 } 
    ::= { cLReapGroupConfigEntry 2 }

cLReapGroupSecondaryRadiusIndex OBJECT-TYPE
    SYNTAX          Unsigned32
    MAX-ACCESS      read-create
    STATUS          current
    DESCRIPTION
        "The object specifies the value that maps to the
        secondary RADIUS server for this group. 
	
	A value of '0' indicates that the secondary RADIUS
	server is not configured for this group."
    DEFVAL          { 0 } 
    ::= { cLReapGroupConfigEntry 3 }

cLReapGroupStorageType OBJECT-TYPE
    SYNTAX          StorageType
    MAX-ACCESS      read-create
    STATUS          current
    DESCRIPTION
        "This object specifies the storage type for this conceptual
        row." 
    ::= { cLReapGroupConfigEntry 4 }

cLReapGroupRowStatus OBJECT-TYPE
    SYNTAX          RowStatus
    MAX-ACCESS      read-create
    STATUS          current
    DESCRIPTION
        "This object specifies the status column for a
        conceptual row in this table." 
    ::= { cLReapGroupConfigEntry 5 }

cLReapGroupRadiusPacTimeout  OBJECT-TYPE
        SYNTAX Unsigned32(0..4095)
        UNITS  "Seconds"
        MAX-ACCESS read-create
        STATUS     deprecated
        DESCRIPTION
            "This object represents timeout value for the
        PAC (protected access credentials). Superceded
        by cLReapGroupRadiusPacTimeoutCtrl."
        DEFVAL { 10 }
        ::= { cLReapGroupConfigEntry 6 }

cLReapGroupRadiusAuthorityId  OBJECT-TYPE
        SYNTAX OCTET STRING (SIZE(0..32))
        MAX-ACCESS read-create
        STATUS     current
        DESCRIPTION
            "This object specifies the authority ID used 
	    for client association when client uses EAP-FAST
	    mechanism." 
        DEFVAL { "" }
        ::= { cLReapGroupConfigEntry 7 }

cLReapGroupRadiusAuthorityInfo  OBJECT-TYPE
        SYNTAX OCTET STRING (SIZE(0..32))
        MAX-ACCESS read-create
        STATUS     current
        DESCRIPTION
            "This object specifies the authority information 
	    used for client association when client uses
	    EAP-FAST mechanism."
        DEFVAL { "" }
        ::= { cLReapGroupConfigEntry 8 }

cLReapGroupRadiusServerKey OBJECT-TYPE
    SYNTAX          OCTET STRING (SIZE  (1..32))
    MAX-ACCESS      read-create
    STATUS          current
    DESCRIPTION
        "This object specifies the RADIUS server key. For security
        the key always returns '****'."
    DEFVAL          { "****" } 
    ::= { cLReapGroupConfigEntry 9 }

cLReapGroupRadiusIgnoreKey OBJECT-TYPE
    SYNTAX          TruthValue
    MAX-ACCESS      read-create
    STATUS          current
    DESCRIPTION
        "This object specifies whether anonymous provisioning
        is enabled. A value of 'true' indicates the controller 
        will ignore the key configured in cLReapGroupRadiusServerKey 
        anonymous requests. A value of 'false' 
        indicates that the controller will use the key configured 
        by cLReapGroupRadiusServerKey."
    DEFVAL          { true } 
    ::= { cLReapGroupConfigEntry 10 }

cLReapGroupRadiusEnable OBJECT-TYPE
    SYNTAX          TruthValue
    MAX-ACCESS      read-create
    STATUS          current
    DESCRIPTION
        "This parameter specifies whether RADIUS is enabled.
        A value of 'true' specifies that RADIUS is enabled. 
        A value of 'false' specifies that RADIUS is disabled."
    DEFVAL          { false } 
    ::= { cLReapGroupConfigEntry 11 }

cLReapGroupRadiusLeapEnable OBJECT-TYPE
    SYNTAX          TruthValue
    MAX-ACCESS      read-create
    STATUS          current
    DESCRIPTION
        "This parameter specifies whether LEAP is enabled.
        A value of 'true' specifies that LEAP is enabled. 
        A value of 'false' specifies that LEAP is disabled."
    DEFVAL          { false } 
    ::= { cLReapGroupConfigEntry 12 }

cLReapGroupRadiusEapFastEnable OBJECT-TYPE
    SYNTAX          TruthValue
    MAX-ACCESS      read-create
    STATUS          current
    DESCRIPTION
        "This parameter specifies whether EAP-FAST is enabled.
        A value of 'true' specifies that EAP-FAST is enabled. 
        A value of 'false' specifies that EAP-FAST is disabled."
    DEFVAL          { false } 
    ::= { cLReapGroupConfigEntry 13 }

cLReapGroupRadiusPacTimeoutCtrl OBJECT-TYPE
    SYNTAX          Unsigned32 (0..4095)
    UNITS           "seconds"
    MAX-ACCESS      read-create
    STATUS          current
    DESCRIPTION
        "This parameter specifies timeout value for the
        PAC (protected access credentials). 
        Valid range of timeout is 2 to 4095, 
        and value 0 stands for disable."
    DEFVAL          { 10 } 
    ::= { cLReapGroupConfigEntry 14 }
 
cLReapGroupEfficientApUpgradeEnable  OBJECT-TYPE
        SYNTAX TruthValue
        MAX-ACCESS read-create
        STATUS     current
        DESCRIPTION
            "This parameter specifies whether efficient AP image
             upgrade is enabled. A value of 'true' indicates that 
             efficient AP image upgrade is enabled. A value of 'false'
             indicates that Efficient AP image upgrade is disabled."
        DEFVAL { false }
        ::= { cLReapGroupConfigEntry 15 }
        
cLReapGroupApUpgradeStart  OBJECT-TYPE
     SYNTAX      INTEGER {
                 initiatePrimary(1),
                 initiateBackup(2),
                 abort(3)
              }
     MAX-ACCESS  read-create
     STATUS      current
     DESCRIPTION
          "This object specifies which image REAP AP has to download 
	  from WLC upon upgrade start.
	  
	  A value of 'initiatePrimary' specifies AP will download
	  primary image from WLC.
	  
	  A value of 'initiateBackup' specifies AP will download
	  backup image from WLC.
	  
	  A value of 'abort' specifies AP will stop the download 
	  process."
     ::= { cLReapGroupConfigEntry 16 }

cLReapGroupSlaveMaxRetryCount OBJECT-TYPE
        SYNTAX     Unsigned32
        MAX-ACCESS read-create
        STATUS     current
        DESCRIPTION
                 " This object specifies the maximum retries the
                  the slave AP has to try to download image
                  from the master in the hreap group before it
		  stars download from WLC. Range is 1 to 63"
		  
        ::= { cLReapGroupConfigEntry 17 }

cLReapGroupPrimaryRadiusServerType OBJECT-TYPE
         SYNTAX      InetAddressType
         MAX-ACCESS  read-create
         STATUS      current
         DESCRIPTION
                "This object specifies server IP address type of the 
		primary radius server for the flexconnect group."
         ::= { cLReapGroupConfigEntry 18 }

cLReapGroupPrimaryRadiusServerAddress OBJECT-TYPE
         SYNTAX      InetAddress
         MAX-ACCESS  read-create
         STATUS      current
         DESCRIPTION
                "This object specifies server IP address  of the 
		primary radius server for the flexconnect group."
         ::= { cLReapGroupConfigEntry 19 }

cLReapGroupPrimaryRadiusServerPort OBJECT-TYPE
         SYNTAX      Unsigned32
         MAX-ACCESS  read-create
         STATUS      current
         DESCRIPTION
                "This object specifies port number of the primary 
		radius server for the flexconnect group."
         ::= { cLReapGroupConfigEntry 20 }

cLReapGroupPrimaryServerSecret OBJECT-TYPE
         SYNTAX      SnmpAdminString
         MAX-ACCESS  read-create
         STATUS      current
         DESCRIPTION
                "This object specifies secret of the primary radius
		 server for the flexconnect group."
         ::= { cLReapGroupConfigEntry 21 }

cLReapGroupSecRadiusServerType OBJECT-TYPE
         SYNTAX      InetAddressType
         MAX-ACCESS  read-create
         STATUS      current
         DESCRIPTION
                "This object specifies server IP address type of the 
		secondary radius server for the flexconnect group."
         ::= { cLReapGroupConfigEntry 22 }

cLReapGroupSecRadiusServerAddress OBJECT-TYPE
         SYNTAX      InetAddress
         MAX-ACCESS  read-create
         STATUS      current
         DESCRIPTION
                "This object specifies server IP address  of the 
		secondary radius server for the flexconnect group."
         ::= { cLReapGroupConfigEntry 23 }

cLReapGroupSecRadiusServerPort OBJECT-TYPE
         SYNTAX      Unsigned32
         MAX-ACCESS  read-create
         STATUS      current
         DESCRIPTION
                "This object specifies port number of the secondary 
		radius server for the flexconnect group."
         ::= { cLReapGroupConfigEntry 24 }

cLReapGroupSecServerSecret OBJECT-TYPE
         SYNTAX      SnmpAdminString 
         MAX-ACCESS  read-create
         STATUS      current
         DESCRIPTION
                "This object specifies secret of the secondary 
		radius server for the flexconnect group."
         ::= { cLReapGroupConfigEntry 25 }

cLReapGroupRadiusPeapEnable  OBJECT-TYPE
        SYNTAX TruthValue
        MAX-ACCESS read-create
        STATUS     current
        DESCRIPTION
            "This parameter specifies whether PEAP is enabled for
	    that flexconect group.
            A value of 'true' indicates that PEAP is enabled.
            A value of 'false' indicates that PEAP is disabled."
        DEFVAL { false }
        ::= { cLReapGroupConfigEntry 26 }

cLReapGroupRadiusEapTlsEnable  OBJECT-TYPE
        SYNTAX TruthValue
        MAX-ACCESS read-create
        STATUS     current
        DESCRIPTION
            "This parameter specifies whether EAP-TLS is enabled
	    in the flexconect group.
       	    A value of 'true' indicates that EAP-TLS is enabled.
            A value of 'false' indicates that EAP-TLS is disabled."
        DEFVAL { false }
        ::= { cLReapGroupConfigEntry 27 }

cLReapGroupCertificateEapTlsEnable  OBJECT-TYPE
        SYNTAX TruthValue
        MAX-ACCESS read-create
        STATUS     current
        DESCRIPTION
            "This parameter specifies whether certificate for
        EAP-TLS is enabled.
        A value of 'true' indicates that EAP-TLS certificate
        is enabled.
        A value of 'false' indicates that EAP-TLS certificate
        is disabled."
        DEFVAL { false }
        ::= { cLReapGroupConfigEntry 28 }

cLReapGroupNativeVlanId OBJECT-TYPE
        SYNTAX     Unsigned32 (1..4095)
        MAX-ACCESS read-create
        STATUS     current
        DESCRIPTION
                "This object specifies the Native VLAN ID for the
                particular flexconenct group identified by 
		cLReapGroupName."
        DEFVAL { 1 }
        ::= { cLReapGroupConfigEntry 29 }

cLReapGroupVlanEnable OBJECT-TYPE
        SYNTAX     TruthValue     
        MAX-ACCESS read-create
        STATUS     current
        DESCRIPTION
                "This object specifies the availability of Native
                VLAN configured through cLReapGroupNativeVlanId on
                this REAP group.

                A value of 'true' indicates that the VLAN configured
                as native through cLReapGroupNativeVlanId is enabled
                on the REAP and that the REAP can reach the
                controller through the native VLAN.

                A value of 'false' indicates that the VLAN configured
                as native through cLReapGroupNativeVlanId is disabled
                and the REAP can reach the controller using its 
		management VLAN"
        DEFVAL  { false }
        ::= { cLReapGroupConfigEntry 30 }

cLReapGroupOverrideVlanEnable OBJECT-TYPE
        SYNTAX     TruthValue     
        MAX-ACCESS read-create
        STATUS     current
        DESCRIPTION
                "This object specifies the overriding of vlans at REAP 
                APs by the vlans available from the reap group."
        DEFVAL  { false }
        ::= { cLReapGroupConfigEntry 31 }

cLReapGroupHttpProxyIpType OBJECT-TYPE
         SYNTAX            InetAddressType
         MAX-ACCESS        read-create
         STATUS            current
         DESCRIPTION
            "Thsi object specifies Ip Address type of Http proxy in 
	    flexconnect group."
         ::= { cLReapGroupConfigEntry 32 }

cLReapGroupHttpProxyIp OBJECT-TYPE
         SYNTAX        InetAddress
         MAX-ACCESS    read-create
         STATUS        current
         DESCRIPTION
            "This object specifies HTTP proxy Ip address in 
	    flexconect group. "
         ::= { cLReapGroupConfigEntry 33 }

cLReapGroupHttpProxyPort OBJECT-TYPE
         SYNTAX          Unsigned32
         MAX-ACCESS      read-create
         STATUS          current
         DESCRIPTION
              "This object specifies HTTP Proxy port in flexconnect
	      group."
         ::= { cLReapGroupConfigEntry 34 }

cLReapGroupVlanTemplateName OBJECT-TYPE
        SYNTAX     SnmpAdminString     
        MAX-ACCESS read-create
        STATUS     current
        DESCRIPTION
                "This object specifies the vlan template name at REAP 
                APs by the vlans available from the reap group."
        DEFVAL  { "" }
        ::= { cLReapGroupConfigEntry 35 }
cLReapGroupEfficientApJoinEnable  OBJECT-TYPE
        SYNTAX TruthValue
        MAX-ACCESS read-create
        STATUS     current
        DESCRIPTION
            "This parameter specifies whether efficient AP image
             join is enabled. A value of 'true' indicates that 
             efficient AP image upgrade is enabled. A value of 'false'
             indicates that Efficient AP image upgrade is disabled."
        DEFVAL { true }
        ::= { cLReapGroupConfigEntry 36 }

cLReapGroupAutoApTypeConversion  OBJECT-TYPE
        SYNTAX TruthValue
        MAX-ACCESS read-create
        STATUS     current
        DESCRIPTION
            "This parameter specifies if auto aptype conversion 
             is enabled. A value of 'true' indicates that 
             auto aptype conversion is enabled. A value of 'false'
             indicates that auto aptype conversion is disabled."
        DEFVAL { true }
        ::= { cLReapGroupConfigEntry 37 }

-- ********************************************************************
-- Hybrid REAP Group AP configuration
-- ********************************************************************

cLReapGroupApConfigTable OBJECT-TYPE
    SYNTAX          SEQUENCE OF CLReapGroupApConfigEntry 
    MAX-ACCESS      not-accessible
    STATUS          current
    DESCRIPTION
        "This table represents the group associated with
        an AP. Entries are added or deleted by the user 
        through the use of cLReapGroupApRowStatus."
    ::= { ciscoLwappReapGroupConfig 2 }

cLReapGroupApConfigEntry OBJECT-TYPE
    SYNTAX          CLReapGroupApConfigEntry
    MAX-ACCESS      not-accessible
    STATUS          current
    DESCRIPTION
        "Each entry represents a conceptual row in
        cLReapGroupApConfigTable."
    INDEX           {
                        cLReapGroupName,
                        cLApSysMacAddress
                    } 
    ::= { cLReapGroupApConfigTable 1 }

CLReapGroupApConfigEntry ::= SEQUENCE {
        cLReapGroupApStorageType StorageType,
        cLReapGroupApRowStatus   RowStatus,
        cLReapGroupApEntryType   INTEGER,
        cLReapGroupApPnPConflict TruthValue
}

cLReapGroupApStorageType OBJECT-TYPE
    SYNTAX          StorageType
    MAX-ACCESS      read-create
    STATUS          current
    DESCRIPTION
        "This object specifies the storage type for this conceptual
        row." 
    ::= { cLReapGroupApConfigEntry 1 }

cLReapGroupApRowStatus OBJECT-TYPE
    SYNTAX          RowStatus
    MAX-ACCESS      read-create
    STATUS          current
    DESCRIPTION
        "This object specifies the status column for a
        conceptual row in this table." 
    ::= { cLReapGroupApConfigEntry 2 }
 
cLReapGroupApEntryType OBJECT-TYPE
        SYNTAX     INTEGER{
                       admin(1),
                       cloud(2)
                   } 
        MAX-ACCESS read-only
        STATUS     current
        DESCRIPTION
                "This object represents the entry type of the AP.
		A value of 'admin' represents the AP added to group
		by manual admin configuration
		A value of 'cloud' represents the AP added to group
		because of AP configured from cloud to join this 
		group."
        ::= { cLReapGroupApConfigEntry 3 }

cLReapGroupApPnPConflict OBJECT-TYPE
        SYNTAX     TruthValue
        MAX-ACCESS read-only
        STATUS     current
        DESCRIPTION
                "This object represents whether there is any conflict 
                with the flexconnect group value from PnP."
        ::= { cLReapGroupApConfigEntry 4 }
 
-- ********************************************************************
-- Hybrid REAP Group User configuration
-- ********************************************************************

cLReapGroupUserConfigTable OBJECT-TYPE
    SYNTAX          SEQUENCE OF CLReapGroupUserConfigEntry 
    MAX-ACCESS      not-accessible
    STATUS          current
    DESCRIPTION
        "This table represents the group associated with
        an User. Entries are added or deleted by the 
        application through the use of 
        cLReapGroupUserRowStatus."
    ::= { ciscoLwappReapGroupConfig 3 }

cLReapGroupUserConfigEntry OBJECT-TYPE
    SYNTAX          CLReapGroupUserConfigEntry
    MAX-ACCESS      not-accessible
    STATUS          current
    DESCRIPTION
        "Each entry represents a conceptual row in
        cLReapGroupUserConfigTable."
    INDEX           {
                        cLReapGroupName,
                        cLReapGroupUserName
                    } 
    ::= { cLReapGroupUserConfigTable 1 }

CLReapGroupUserConfigEntry ::= SEQUENCE {
        cLReapGroupUserName        SnmpAdminString,
        cLReapGroupUserPassword    SnmpAdminString,
        cLReapGroupUserStorageType StorageType,
        cLReapGroupUserRowStatus   RowStatus
}

cLReapGroupUserName OBJECT-TYPE
    SYNTAX          SnmpAdminString (SIZE  (1..24))
    MAX-ACCESS      not-accessible
    STATUS          current
    DESCRIPTION
        "This object represents the user name for this
        group. user name is used for authenticating a
              client associated to an AP within the group." 
    ::= { cLReapGroupUserConfigEntry 1 }

cLReapGroupUserPassword OBJECT-TYPE
    SYNTAX          SnmpAdminString (SIZE  (1..64))
    MAX-ACCESS      read-create
    STATUS          current
    DESCRIPTION
        "This object specifies the password for this
        user." 
    ::= { cLReapGroupUserConfigEntry 2 }

cLReapGroupUserStorageType OBJECT-TYPE
    SYNTAX          StorageType
    MAX-ACCESS      read-create
    STATUS          current
    DESCRIPTION
        "This object specifies the storage type for this
        conceptual row." 
    ::= { cLReapGroupUserConfigEntry 3 }

cLReapGroupUserRowStatus OBJECT-TYPE
    SYNTAX          RowStatus
    MAX-ACCESS      read-create
    STATUS          current
    DESCRIPTION
        "This object specifies the status column for a
        conceptual row in this table." 
    ::= { cLReapGroupUserConfigEntry 4 }
 
-- ********************************************************************
-- Hybrid REAP Group vlan-acl configuration
-- ********************************************************************
cLReapGroupVlanAclTable OBJECT-TYPE
        SYNTAX     SEQUENCE OF CLReapGroupVlanAclEntry
        MAX-ACCESS not-accessible
        STATUS     current
        DESCRIPTION
                "This table represents the configuration of VLAN-ACL 
                mappings for REAP groups."
        ::= { ciscoLwappReapGroupConfig 4 }

cLReapGroupVlanAclEntry OBJECT-TYPE
        SYNTAX     CLReapGroupVlanAclEntry
        MAX-ACCESS not-accessible
        STATUS     current
        DESCRIPTION
                "Each entry represents a conceptual row in
                cLReapGroupVlanAclTable."
        INDEX   { cLReapGroupName, cLReapGroupVlanId }
        ::= { cLReapGroupVlanAclTable 1 }

CLReapGroupVlanAclEntry ::=
        SEQUENCE {
                   cLReapGroupVlanId      Unsigned32,
                   cLReapGroupIngressAcl  SnmpAdminString,
                   cLReapGroupEgressAcl   SnmpAdminString,
                   cLReapGroupVlanAclRowStatus RowStatus,
                   cLReapGroupVlanOrder      Unsigned32
        }


cLReapGroupVlanId OBJECT-TYPE
        SYNTAX     Unsigned32 (1..4095)
        MAX-ACCESS not-accessible
        STATUS     current
        DESCRIPTION
                "This object represents the VLAN ID to be mapped
                to the ACL for the reap group identified by 
                cLReapGroupName "
     ::= { cLReapGroupVlanAclEntry  1 }
        
cLReapGroupIngressAcl OBJECT-TYPE
      SYNTAX     SnmpAdminString (SIZE(0..32))
      MAX-ACCESS read-create
      STATUS     current
      DESCRIPTION
             "This object specifies the name of the ingress access 
              control list for the vlan-acl mapping for the group
	      identified by cLReapGroupName."
        ::= { cLReapGroupVlanAclEntry  2 }

cLReapGroupEgressAcl OBJECT-TYPE
      SYNTAX     SnmpAdminString (SIZE(0..32))
      MAX-ACCESS read-create
      STATUS     current
      DESCRIPTION
             "This object specifies the name of the egress access 
              control list for the vlan-acl mapping for the group
	      identified by cLReapGroupName."

        ::= { cLReapGroupVlanAclEntry  3 }

cLReapGroupVlanAclRowStatus OBJECT-TYPE
        SYNTAX     RowStatus
        MAX-ACCESS read-create
        STATUS     current
        DESCRIPTION
                "This object specifies the status column for a
                 conceptual row in this table."
        ::= { cLReapGroupVlanAclEntry  4}

cLReapGroupVlanOrder OBJECT-TYPE
    SYNTAX          Unsigned32
    MAX-ACCESS      read-only
    STATUS          current
    DESCRIPTION
        "This object represents the vlan order configuration on the
        group level." 
    ::= { cLReapGroupVlanAclEntry 5 }

-- ********************************************************************
-- Hybrid REAP Group wlan-acl configuration
-- ********************************************************************


cLReapGroupAclTable OBJECT-TYPE
        SYNTAX     SEQUENCE OF CLReapGroupAclEntry
        MAX-ACCESS not-accessible
        STATUS     current
        DESCRIPTION
                "This table represents the configuration of wlan-acl 
                mappings for REAPs."
        ::= { ciscoLwappReapGroupConfig 5 }

cLReapGroupAclEntry OBJECT-TYPE
        SYNTAX     CLReapGroupAclEntry
        MAX-ACCESS not-accessible
        STATUS     current
        DESCRIPTION
                "Each entry represents a conceptual row in
                cLReapGroupAclTable."
        INDEX   { cLReapGroupName, cLWlanIndex }
        ::= { cLReapGroupAclTable 1 }

CLReapGroupAclEntry ::=
        SEQUENCE {
                   cLReapGroupWebAuthAcl   SnmpAdminString,
                   cLReapGroupAclRowStatus RowStatus,
                   cLReapGroupWebAuthIpv6Acl   SnmpAdminString
        }
        
cLReapGroupWebAuthAcl OBJECT-TYPE
      SYNTAX     SnmpAdminString (SIZE(0..32))
      MAX-ACCESS read-create
      STATUS     current
      DESCRIPTION
             "This object specifies the name of the webauth access 
             control list for the wlan-acl mapping in the flexconnect
	     group."
        ::= { cLReapGroupAclEntry  1 }

cLReapGroupAclRowStatus OBJECT-TYPE
        SYNTAX     RowStatus
        MAX-ACCESS read-create
        STATUS     current
        DESCRIPTION
                "This object specifies the status column for a
                 conceptual row in this table."
        ::= { cLReapGroupAclEntry  2}

cLReapGroupWebAuthIpv6Acl OBJECT-TYPE
      SYNTAX     SnmpAdminString (SIZE(0..32))
      MAX-ACCESS read-create
      STATUS     current
      DESCRIPTION
             "This object specifies the name of the Ipv6 webauth access 
             control list for the wlan-acl mapping in the flexconnect
      group."
        ::= { cLReapGroupAclEntry  3 }

cLReapGroupWebPolicyAclTable OBJECT-TYPE
        SYNTAX     SEQUENCE OF CLReapGroupWebPolicyAclEntry
        MAX-ACCESS not-accessible
        STATUS     current
        DESCRIPTION
                "This table represents the configuration of webpolicy 
                acl mappings for REAP groups."
        ::= { ciscoLwappReapGroupConfig 6 }

cLReapGroupWebPolicyAclEntry OBJECT-TYPE
        SYNTAX     CLReapGroupWebPolicyAclEntry
        MAX-ACCESS not-accessible
        STATUS     current
        DESCRIPTION
                "Each entry represents a conceptual row in the
                cLReapGroupWebPolicyAclTable."
        INDEX   { cLReapGroupName, cLReapGroupWebPolicyAcl }
        ::= { cLReapGroupWebPolicyAclTable 1 }

CLReapGroupWebPolicyAclEntry ::=
        SEQUENCE {
                   cLReapGroupWebPolicyAcl            SnmpAdminString,
                   cLReapGroupWebPolicyAclRowStatus   RowStatus,
                   cLReapGroupWebPolicyAclType        INTEGER
                  }

cLReapGroupWebPolicyAcl OBJECT-TYPE
      SYNTAX     SnmpAdminString (SIZE(0..32))
      MAX-ACCESS not-accessible
      STATUS     current
      DESCRIPTION
             "This object specifies the name of the webpolicy access 
             control aist to be mapped to the REAP group."
        ::= { cLReapGroupWebPolicyAclEntry  1 }

cLReapGroupWebPolicyAclRowStatus OBJECT-TYPE
        SYNTAX     RowStatus
        MAX-ACCESS read-create
        STATUS     current
        DESCRIPTION
                "This object specifies the status column for a
                 conceptual row in this table."
        ::= { cLReapGroupWebPolicyAclEntry  2}

cLReapGroupWebPolicyAclType OBJECT-TYPE
    SYNTAX          INTEGER  {
                        ipv4(1),
                        ipv6(2)
                    }
    MAX-ACCESS      read-create
    STATUS          current
    DESCRIPTION
        "This object specifies whether webpolicy access control list
         is IPv4 or IPv6."
    DEFVAL          { ipv4 } 
    ::= { cLReapGroupWebPolicyAclEntry 3 }


cLReapGroupLocalSplitAclTable OBJECT-TYPE
        SYNTAX     SEQUENCE OF CLReapGroupLocalSplitAclEntry
        MAX-ACCESS not-accessible
        STATUS     current
        DESCRIPTION
                "This table represents the configuration of WLAN-ACL 
                mappings for local split tunneling at REAP groups."
        ::= { ciscoLwappReapGroupConfig 7 }

cLReapGroupLocalSplitAclEntry OBJECT-TYPE
        SYNTAX     CLReapGroupLocalSplitAclEntry
        MAX-ACCESS not-accessible
        STATUS     current
        DESCRIPTION
                "Each entry represents a conceptual row in
                cLReapGroupLocalSplitAclTable."
        INDEX   { cLReapGroupName, cLWlanIndex }
        ::= { cLReapGroupLocalSplitAclTable 1 }

CLReapGroupLocalSplitAclEntry ::=
        SEQUENCE {
                   cLReapGroupLocalSplitAcl  SnmpAdminString,
                   cLReapGroupLocalSplitAclRowStatus RowStatus
        }

cLReapGroupLocalSplitAcl OBJECT-TYPE
      SYNTAX     SnmpAdminString (SIZE(0..32))
      MAX-ACCESS read-create
      STATUS     current
      DESCRIPTION
             "This object specifies the name of the local split 
	     access control list to be mapped to the WLAN inside
	     REAP group"
        ::= { cLReapGroupLocalSplitAclEntry  1 }

cLReapGroupLocalSplitAclRowStatus OBJECT-TYPE
        SYNTAX     RowStatus
        MAX-ACCESS read-create
        STATUS     current
        DESCRIPTION
                "This object specifies the status column for a 
		conceptual row in this table."
        ::= { cLReapGroupLocalSplitAclEntry  2}

--********************************************************************
--*    Cisco REAP Central DHCP configuration
--********************************************************************

cLReapGroupCentralDhcpTable OBJECT-TYPE
        SYNTAX     SEQUENCE OF CLReapGroupCentralDhcpEntry
        MAX-ACCESS not-accessible
        STATUS     current
        DESCRIPTION
                "This table represents the configuration of central 
                dhcp processing for REAP APs in REAP groups"
        ::= { ciscoLwappReapGroupConfig 8 }
	
cLReapGroupCentralDhcpEntry OBJECT-TYPE
        SYNTAX     CLReapGroupCentralDhcpEntry
        MAX-ACCESS not-accessible
        STATUS     current
        DESCRIPTION
                "Each entry represents a conceptual row in
                cLReapGroupCentralDhcpTable."
        INDEX   { cLReapGroupName, cLWlanIndex }
        ::= { cLReapGroupCentralDhcpTable 1 }
	
CLReapGroupCentralDhcpEntry ::=
        SEQUENCE {
                cLReapGroupDhcpCentral      TruthValue,
                cLReapGroupDhcpOverrideDNS  TruthValue,
                cLReapGroupNatPatEnabled    TruthValue,
                cLReapGroupDhcpRowStatus RowStatus
        }
	
cLReapGroupDhcpCentral OBJECT-TYPE
    SYNTAX     TruthValue
    MAX-ACCESS read-create
    STATUS     current
    DESCRIPTION
    	    "This object specifies the behavior of the REAP AP
	    part of REAP group when switching the DHCP frames of
	    the clients associated to it through the WLAN identified
            by cLWlanIndex.
	    
	    A value of 'true' specifies REAP AP will tunnel
	    DHCP packets to WLC.
	    
	    A value of 'false' specifies REAP AP will bridge
	    DHCP packets locally.
	    
	    This config is applicable only for locally
	    switched WLANs."
	    
    DEFVAL  { false }
    ::= { cLReapGroupCentralDhcpEntry 1 }
    
cLReapGroupDhcpOverrideDNS OBJECT-TYPE
    SYNTAX     TruthValue
    MAX-ACCESS read-create
    STATUS     current
    DESCRIPTION
            "This object specifies the behavior of the REAP AP 
	    part of REAP group when switching the DNS frames 
	    of the clients associated to it through the WLAN 
	    identified by cLWlanIndex.
	    
	    A value of 'true' specifies REAP AP will tunnel
	    DNS packets to WLC.
	    
	    A value of 'false' specifies REAP AP will bridge
	    DNS packets locally.
	    
	    This config is applicable only for locally
	    switched WLANs and when cLReapApDhcpCentral is set to
	    'true'. "
    DEFVAL  { false }
    ::= { cLReapGroupCentralDhcpEntry 2 }
cLReapGroupNatPatEnabled OBJECT-TYPE
    SYNTAX     TruthValue
    MAX-ACCESS read-create
    STATUS     current
    DESCRIPTION
            "This object specifies whether Network Address
            Translation (NAT) and Port Address Trnaslation (PAT)
            are enabled on this REAP AP part of REAP group for 
	    the WLAN identified by cLWlanIndex.
	    
	    A value of 'true' specifies REAP AP will bridge data
	    packets locally after appliying NAT and PAT.
	    
	    A value of 'false' specifies REAP AP will bridge data
	    packets locally without appliying NAT and PAT.
	    
	    This config is applicable only for locally
	    switched WLANs and when cLReapApDhcpCentral is set to
	    'true'. "
    DEFVAL  { false }
    ::= { cLReapGroupCentralDhcpEntry 3 }


cLReapGroupDhcpRowStatus OBJECT-TYPE
        SYNTAX     RowStatus
        MAX-ACCESS read-create
        STATUS     current
        DESCRIPTION
                "This object represents the status column for a
                conceptual row in this table."
        ::= { cLReapGroupCentralDhcpEntry 4 }

--********************************************************************
--*    Cisco REAP WLAN / VLAN Id mapping configuration 
--********************************************************************

cLReapGroupVlanIdTable OBJECT-TYPE
        SYNTAX     SEQUENCE OF CLReapGroupVlanIdEntry
        MAX-ACCESS not-accessible  
        STATUS     current
        DESCRIPTION
                "This table represents the WLAN / VLAN Id mappings
		to be configured for the REAP identified by
                REAP group name.

                VLAN Id configured through this table is passed to
                the respective REAP group identified by the 
                REAP group name. "
        ::= { ciscoLwappReapGroupConfig 9 }
 
cLReapGroupVlanIdEntry OBJECT-TYPE
        SYNTAX     CLReapGroupVlanIdEntry
        MAX-ACCESS not-accessible  
        STATUS     current
        DESCRIPTION
                "Each entry represents a conceptual row that
                corresponds to one WLAN / VLAN Id mapping to 
                be applied to the REAP identified by
                cLReapGroupName. "
        INDEX   { cLReapGroupName, cLWlanIndex }
        ::= { cLReapGroupVlanIdTable 1 }

CLReapGroupVlanIdEntry ::=
        SEQUENCE {
                cLReapGroupWlanVlanId      Unsigned32,
                cLReapGroupVlanRowStatus RowStatus
        }

cLReapGroupWlanVlanId OBJECT-TYPE
        SYNTAX     Unsigned32 (1..4095)
        MAX-ACCESS read-create
        STATUS     current
        DESCRIPTION
                "This object specifies the VLAN ID to be mapped 
                to the WLAN identified by cLWlanIndex in the REAP
		group. " 
        DEFVAL  { 1 } 
        ::= { cLReapGroupVlanIdEntry  1 }

cLReapGroupVlanRowStatus OBJECT-TYPE
        SYNTAX     RowStatus
        MAX-ACCESS read-create
        STATUS     current
        DESCRIPTION
         "This object specifies the reap group vlan mapping row 
         status."        
        
        ::= { cLReapGroupVlanIdEntry  2 }


--********************************************************************
--*    Cisco REAP WLAN / AVC parameters mapping configuration 
--********************************************************************

cLReapGroupAVCFlexTable OBJECT-TYPE
        SYNTAX     SEQUENCE OF CLReapGroupAVCFlexEntry
        MAX-ACCESS not-accessible  
        STATUS     current
        DESCRIPTION
                "This table represents the WLAN / AVC parameters 
		mappings to be configured for the REAP identified by
                REAP group name.

                AVC parameters configured through this table is passed 
                to the respective REAP group identified by the 
                REAP group name. "
        ::= { ciscoLwappReapGroupConfig 10 }
 
cLReapGroupAVCFlexEntry OBJECT-TYPE
        SYNTAX     CLReapGroupAVCFlexEntry
        MAX-ACCESS not-accessible  
        STATUS     current
        DESCRIPTION
                "Each entry represents a conceptual row that
                corresponds to one WLAN / AVC parameters mapping to 
                be applied to the REAP identified by
                cLReapGroupName. "
        INDEX   { cLReapGroupName, cLWlanIndex }
        ::= { cLReapGroupAVCFlexTable 1 }

CLReapGroupAVCFlexEntry ::= SEQUENCE {
            cLReapGroupAVCFlexProfileName            SnmpAdminString,
            cLReapGroupNbarStatsVisibilityEnable     INTEGER, 
            cLReapGroupAVCFlexRowStatus              RowStatus
        }

cLReapGroupAVCFlexProfileName OBJECT-TYPE
        SYNTAX          SnmpAdminString (SIZE(0..32))
        MAX-ACCESS      read-create
        STATUS          current
        DESCRIPTION
        "This object specifies the AVC profile name assigned
         to this WLAN in the REAP idendified by cLReapGroupName.
         'none' specifies no profile is being associated.
         profile name 'none' should be used to de-associate profile 
         from WLAN in the REAP idendified by cLReapGroupName."
        ::= { cLReapGroupAVCFlexEntry 1 }

cLReapGroupNbarStatsVisibilityEnable OBJECT-TYPE
        SYNTAX          INTEGER {
                            disable(1),
                            enable(2),
                            wlan-specific(3)
                        }

        MAX-ACCESS      read-create
        STATUS          current
        DESCRIPTION
        "This object specifies the user to enable or disable 
	 NBAR stats visibility.
         A value of 'disable' indicates NBAR stats visibility
	 is disabled.
         A value of 'enable' indicates NBAR stats visibility 
	 is enabled.
         A value of 'wlan-specific' indicates NBAR stats 
	 visbility is wlan-specific."
        ::= { cLReapGroupAVCFlexEntry 2 }

cLReapGroupAVCFlexRowStatus OBJECT-TYPE
        SYNTAX     RowStatus
        MAX-ACCESS read-create
        STATUS     current
        DESCRIPTION
                "This object specifies the rowstatus of the reap 
		group wlan avc parameter mappings table."
        ::= { cLReapGroupAVCFlexEntry  3 }

--********************************************************************
--*    Cisco REAP Master AP Configuration
--********************************************************************

cLReapMasterApConfigTable OBJECT-TYPE
        SYNTAX     SEQUENCE OF CLReapMasterApConfigEntry
        MAX-ACCESS not-accessible
        STATUS     current
        DESCRIPTION
                "This table represents the master AP admin 
                configuration of REAPs.

                The agent adds a row to this table corresponding to
                each row representing a REAP in cLApTable of the
                CISCO-LWAPP-AP-MIB.  The agent deletes the row
                either when the AP dissociates from the
                controller or moved out of the remote mode. "
        ::= { ciscoLwappReapMasterApConfig 1 }

cLReapMasterApConfigEntry OBJECT-TYPE
        SYNTAX     CLReapMasterApConfigEntry
        MAX-ACCESS not-accessible
        STATUS     current
        DESCRIPTION
                "Each entry represents a conceptual row in
                cLReapMasterApConfigTable and corresponds to the
                Master configuration of a REAP. "
        INDEX   { cLReapGroupName, cLApSysMacAddress }
        ::= { cLReapMasterApConfigTable 1 }

CLReapMasterApConfigEntry ::=
        SEQUENCE {
                cLReapMasterApModel   SnmpAdminString,
                cLReapMasterApManual    TruthValue,
                cLReapMasterApRowStatus RowStatus 
        }


cLReapMasterApModel OBJECT-TYPE
    SYNTAX     SnmpAdminString 
    MAX-ACCESS read-only
    STATUS current
    DESCRIPTION
        "The object represents the model of the AP in the 
	hreap group. This AP will be the master in the efficient
	upgrade process. "
        ::= { cLReapMasterApConfigEntry 1 }

cLReapMasterApManual OBJECT-TYPE
         SYNTAX     TruthValue
         MAX-ACCESS read-only
         STATUS     current
         DESCRIPTION
         	"This object represents if this REAP AP is
                 manually configured by the user.
                 A value of 'true' indicates that this REAP master is
                 manually configured.
                 A value of 'false' indicates that this REAP master is
                 not manually configured."
         ::= {  cLReapMasterApConfigEntry 2 }


cLReapMasterApRowStatus OBJECT-TYPE
      SYNTAX     RowStatus
      MAX-ACCESS read-create
      STATUS     current
      DESCRIPTION
             "This object specifies the row Status of the Master 
             table."
      ::= { cLReapMasterApConfigEntry 3 }

-- *******************************************************************
-- cLReapL2AclTable
-- *******************************************************************

cLReapL2AclTable OBJECT-TYPE
      SYNTAX     SEQUENCE OF CLReapL2AclEntry
      MAX-ACCESS not-accessible
      STATUS     current
      DESCRIPTION
            "The table listing layer2 ACLs (access control lists) 
             on the switch."
      ::= { ciscoLwappReapAclConfig 3 }


cLReapL2AclEntry OBJECT-TYPE
      SYNTAX    CLReapL2AclEntry
      MAX-ACCESS not-accessible
      STATUS     current
      DESCRIPTION
            "Each entry represents the attributes for 
            cLReapL2AclTable.An entry gets added to the 
            table on creating a layer2 ACL."
      INDEX      { cLReapL2AclName }
      ::= { cLReapL2AclTable 1 }

CLReapL2AclEntry ::= SEQUENCE {
                cLReapL2AclName          SnmpAdminString,
                cLReapL2AclApplyMode     INTEGER,
                cLReapL2AclRowStatus     RowStatus
           }

cLReapL2AclName OBJECT-TYPE
      SYNTAX     SnmpAdminString (SIZE(1..32))
      MAX-ACCESS not-accessible
      STATUS     current
      DESCRIPTION
             "This object represents name of the L2 ACL on the
	     switch."
      ::= { cLReapL2AclEntry 1 }

cLReapL2AclApplyMode OBJECT-TYPE
    SYNTAX          INTEGER  {
                        notapplied(1),
                        applied(2)
                    }
      MAX-ACCESS read-only
      STATUS     current
      DESCRIPTION
             "This object represents the apply mode of the L2ACL on 
	     the switch. 
	     Mode value 'applied' means the L2ACL has been 
             applied on the switch. 
	     Default mode on creation on ACL will be notapplied."
      ::= { cLReapL2AclEntry 2 }

cLReapL2AclRowStatus OBJECT-TYPE
      SYNTAX     RowStatus
      MAX-ACCESS read-create
      STATUS     current
      DESCRIPTION
             "This object specifies the row Status of the L2ACL."
      ::= { cLReapL2AclEntry 3 }

-- *******************************************************************
-- cLReapL2AclRuleTable
-- *******************************************************************

cLReapL2AclRuleTable OBJECT-TYPE
      SYNTAX     SEQUENCE OF CLReapL2AclRuleEntry
      MAX-ACCESS not-accessible
      STATUS     current
      DESCRIPTION
            "The table represents L2Acl rules(access control list 
	    entries) on the L2ACL with name cLReapL2AclName."
      ::= { ciscoLwappReapAclConfig 4 }

cLReapL2AclRuleEntry OBJECT-TYPE
      SYNTAX     CLReapL2AclRuleEntry
      MAX-ACCESS not-accessible
      STATUS     current
      DESCRIPTION
            "Each entry represents the attributes for 
            clReapL2AclRuleTable. An entry gets added to
             the table on creating a rule on L2ACL."
    INDEX           {
                        cLReapL2AclName,
                        cLReapL2AclRuleIndex
                    }
      ::= { cLReapL2AclRuleTable 1 }

CLReapL2AclRuleEntry ::= SEQUENCE {
                    cLReapL2AclRuleIndex                    Unsigned32,
                    cLReapL2AclRuleAction                   INTEGER,
                    cLReapL2AclRuleEthertype                Unsigned32,
                    cLReapL2AclRuleEthertypeMask            Unsigned32,
                    cLReapL2AclRuleDirection                INTEGER,
                    cLReapL2AclNewRuleIndex                 Unsigned32,
                    cLReapL2AclRuleRowStatus                RowStatus
                }

cLReapL2AclRuleIndex OBJECT-TYPE
      SYNTAX     Unsigned32
      MAX-ACCESS not-accessible
      STATUS     current
      DESCRIPTION
             "This object represents the unique index of the L2ACL rule
	      in REAP L2ACL. This can be updated to reset the sequence 
	      of the rules of an L2ACL. Valid range for this object is
	      1 to 64"
      ::= { cLReapL2AclRuleEntry 1 }

cLReapL2AclRuleAction OBJECT-TYPE
    SYNTAX          INTEGER  {
                        deny(1),
                        permit(2)
                    }
      MAX-ACCESS read-create
      STATUS     current
      DESCRIPTION
             "This object specifies the permission mode of a rule.
	     The value of 'deny' means traffic will be blocked
	     which meets the rule.
	     The value of 'permits' means traffic will be allowed
	     which meets the rule."
      DEFVAL { deny }
      ::= { cLReapL2AclRuleEntry 2 }

cLReapL2AclRuleEthertype OBJECT-TYPE
        SYNTAX Unsigned32(0..65536)
        MAX-ACCESS read-create
        STATUS current
        DESCRIPTION
                "This object specifies the etherType of the L2Acl
		 rule. Default is 0x0"
                 
        DEFVAL { 0 }
        ::= { cLReapL2AclRuleEntry 3 }

cLReapL2AclRuleEthertypeMask OBJECT-TYPE
        SYNTAX Unsigned32(0..65536)
        MAX-ACCESS read-create
        STATUS current
        DESCRIPTION
                "This object specifies the etherType Mask of the 
		L2Acl rule. Default is 0x0"
                 
        DEFVAL { 0 }
        ::= { cLReapL2AclRuleEntry 4 }

cLReapL2AclRuleDirection OBJECT-TYPE
    SYNTAX          INTEGER  {
                        inbound(1),
                        outbound(2),
                        any(3)
                    }
      MAX-ACCESS read-create
      STATUS     current
      DESCRIPTION
             "This object specifies the direction of the packet 
              to which the rule may be applied.
	      A value of 'inbound' specifies that this rule will be 
	      applied on traffic coming into switchport.
	      A value of 'outbound' specifies that this rule will be 
	      applied on traffic going out of switchport.
	      A value of 'any' specifies that this rule will be 
	      applied on both incoming and out going traffic on 
	      switchport. "
      DEFVAL { any }
      ::= { cLReapL2AclRuleEntry 5 }

cLReapL2AclNewRuleIndex OBJECT-TYPE
      SYNTAX Unsigned32(1..64)
      MAX-ACCESS read-create
      STATUS     current
      DESCRIPTION
             "This object specifies the new Index of the L2ACL rule. 
              This attribute should be updated if the requirement is 
              to reset the sequence of the rules of an ACL. A read 
             on this will yield the same value as cLReapL2AclRuleIndex"
      ::= { cLReapL2AclRuleEntry 6 }

cLReapL2AclRuleRowStatus OBJECT-TYPE
      SYNTAX     RowStatus
      MAX-ACCESS read-create
      STATUS     current
      DESCRIPTION
             "This object specifies the status of a conceptual
              row in the ACL Rule Table. This is used to create
              and delete entries in the table."
      ::= { cLReapL2AclRuleEntry 7 }

-- *******************************************************************
-- cLReapAclUrlDomainRuleTable
-- *******************************************************************
cLReapAclUrlDomainRuleTable OBJECT-TYPE
      SYNTAX      SEQUENCE OF CLReapAclUrlDomainRuleEntry
      MAX-ACCESS  not-accessible
      STATUS      current
      DESCRIPTION
            "This table represents url domain acl Rules(url based Access 
            Control List entries) on the ACL with name cLReapAclName."
      ::= { ciscoLwappReapAclConfig 5 }

cLReapAclUrlDomainRuleEntry OBJECT-TYPE
      SYNTAX      CLReapAclUrlDomainRuleEntry 
      MAX-ACCESS  not-accessible
      STATUS      current
      DESCRIPTION
            "Each Entry represents the attributes for cLReapAclUrlDomainRuleTable.
             An Url domain rule entry gets added to the table on creating 
             a rule on flexconnect ACL."
      INDEX           {
                        cLReapAclName,
                        cLReapAclUrlDomainRuleIndex
                    }
      ::= { cLReapAclUrlDomainRuleTable 1 }

CLReapAclUrlDomainRuleEntry::= SEQUENCE {
                    cLReapAclUrlDomainRuleIndex        Unsigned32,
                    cLReapAclUrlDomainRuleUrl          SnmpAdminString,
                    cLReapAclUrlDomainRuleAction       INTEGER,
                    cLReapAclUrlDomainRuleRowStatus    RowStatus
            }

cLReapAclUrlDomainRuleIndex OBJECT-TYPE
      SYNTAX     Unsigned32(1..20)
      MAX-ACCESS not-accessible 
      STATUS     current
      DESCRIPTION
             "This object specifies the index of the Url domain ACL rule. 
              It can be used to reset the sequence of the Url rules of an ACL."
      ::= { cLReapAclUrlDomainRuleEntry 1 }

cLReapAclUrlDomainRuleUrl OBJECT-TYPE
      SYNTAX     SnmpAdminString
      MAX-ACCESS read-create
      STATUS     current
      DESCRIPTION
             "This object specifies the URL name for the url domain rule."
      ::= { cLReapAclUrlDomainRuleEntry 2 }

cLReapAclUrlDomainRuleAction OBJECT-TYPE
    SYNTAX INTEGER  {
                        deny(1),
                        permit(2)
                    }
      MAX-ACCESS read-create
      STATUS     current
      DESCRIPTION
             "This object specifies the permission mode of url domain rule.
	     A value of 'deny' specifies client traffic matches
	     this rule will be blocked.
	     A value of 'permit' specifies client traffic matches
	     this rule will be allowed to pass through."
      DEFVAL { deny }
      ::= { cLReapAclUrlDomainRuleEntry 3 }

cLReapAclUrlDomainRuleRowStatus OBJECT-TYPE
      SYNTAX     RowStatus
      MAX-ACCESS read-create
      STATUS     current
      DESCRIPTION
             "This is the status column for this row and is used to
              create and delete specific instances of rows in this table."
      ::= { cLReapAclUrlDomainRuleEntry 4 }


-- *******************************************************************
-- cLReapAclTable
-- *******************************************************************

cLReapAclTable OBJECT-TYPE
      SYNTAX     SEQUENCE OF CLReapAclEntry
      MAX-ACCESS not-accessible
      STATUS     current
      DESCRIPTION
            "The table represents REAP ACLs (access control lists) 
	    on the switch."
      ::= { ciscoLwappReapAclConfig 1 }


cLReapAclEntry OBJECT-TYPE
      SYNTAX    CLReapAclEntry
      MAX-ACCESS not-accessible
      STATUS     current
      DESCRIPTION
            "Each entry represents the attributes for clReapAclTable.
             An entry gets added to the table on creating a 
	     flexconnect ACL."
      INDEX      { cLReapAclName }
      ::= { cLReapAclTable 1 }

CLReapAclEntry ::= SEQUENCE {
                cLReapAclName            SnmpAdminString,
                cLReapAclApplyMode       INTEGER,
                cLReapAclRowStatus       RowStatus,
		cLReapAclUrlDomainListType INTEGER
           }

cLReapAclName OBJECT-TYPE
      SYNTAX     SnmpAdminString (SIZE(1..32))
      MAX-ACCESS not-accessible
      STATUS     current
      DESCRIPTION
             "This object represents name of the REAP 
	     access control list."
      ::= { cLReapAclEntry 1 }

cLReapAclApplyMode OBJECT-TYPE
    SYNTAX          INTEGER  {
                        notapplied(0),
                        applied(1)
                    }
      MAX-ACCESS read-only
      STATUS     current
      DESCRIPTION
             "This object specifies the apply mode of the ACL on the 
             switch. 
	     Mode value 'applied' means the ACL has been 
             applied on the switch.
	     Mode value 'notapplied' means the ACL not applied
	     on the switch."
      ::= { cLReapAclEntry 2 }

cLReapAclRowStatus OBJECT-TYPE
      SYNTAX     RowStatus
      MAX-ACCESS read-create
      STATUS     current
      DESCRIPTION
             "This object specifies the row Status of the ACL."
      ::= { cLReapAclEntry 3 }

cLReapAclUrlDomainListType OBJECT-TYPE
        SYNTAX          INTEGER  {
                          blackList(1),
                          whiteList(2)
                      }
        MAX-ACCESS read-create
        STATUS     deprecated
        DESCRIPTION
		"This object specifies the List type for all the urls being confiured
             on the acl. blackList indicates, access to all the urls configured will
             be denied and whiteList indicates permit. Default value is blackList."
	DEFVAL { blackList }
        ::= { cLReapAclEntry 4 }  

-- *******************************************************************
-- cLReapAclRuleTable
-- *******************************************************************

cLReapAclRuleTable OBJECT-TYPE
      SYNTAX     SEQUENCE OF CLReapAclRuleEntry
      MAX-ACCESS not-accessible
      STATUS     current
      DESCRIPTION
            "The table represents ACL Rules(access control list 
	    entries) on the ACL with name cLReapAclName."
      ::= { ciscoLwappReapAclConfig 2 }

cLReapAclRuleEntry OBJECT-TYPE
      SYNTAX     CLReapAclRuleEntry
      MAX-ACCESS not-accessible
      STATUS     current
      DESCRIPTION
            "Each entry represents the attributes for 
            clReapAclRuleTable. An entry gets added to 
            the table on creating a rule on flexconnect
            ACL."
    INDEX           {
                        cLReapAclName,
                        cLReapAclRuleIndex
                    }
      ::= { cLReapAclRuleTable 1 }

CLReapAclRuleEntry ::= SEQUENCE {
                 cLReapAclRuleIndex                    Unsigned32,
                 cLReapAclRuleAction                   INTEGER,
                 cLReapAclRuleSourceIpAddressType      InetAddressType,
                 cLReapAclRuleSourceIpAddress          InetAddress,
                 cLReapAclRuleSourceIpNetmaskType      InetAddressType,
                 cLReapAclRuleSourceIpNetmask          InetAddress,
                 cLReapAclRuleDestinationIpAddressType InetAddressType,
                 cLReapAclRuleDestinationIpAddress     InetAddress,
                 cLReapAclRuleDestinationIpNetmaskType InetAddressType,
                 cLReapAclRuleDestinationIpNetmask     InetAddress,
                 cLReapAclRuleProtocol                 Unsigned32,
                 cLReapAclRuleStartSourcePort          Unsigned32,
                 cLReapAclRuleEndSourcePort            Unsigned32,
                 cLReapAclRuleStartDestinationPort     Unsigned32,
                 cLReapAclRuleEndDestinationPort       Unsigned32,
                 cLReapAclRuleDscp                     Unsigned32,
                 cLReapAclNewRuleIndex                 Unsigned32,
                 cLReapAclRuleRowStatus                RowStatus
            }

cLReapAclRuleIndex OBJECT-TYPE
      SYNTAX Unsigned32(1..64)
      MAX-ACCESS not-accessible
      STATUS     current
      DESCRIPTION
             "This object represents index of the ACL rule. This can 
	      be updated to reset the sequence of the rules of an ACL."
      ::= { cLReapAclRuleEntry 1 }

cLReapAclRuleAction OBJECT-TYPE
    SYNTAX          INTEGER  {
                        deny(0),
                        permit(1)
                    }
      MAX-ACCESS read-create
      STATUS     current
      DESCRIPTION
             "This object specifies permission mode of the rule.
	     A value of 'deny' specifies client traffic matches
	     this rule will be blocked.
	     A value of 'permit' specifies client traffic matches
	     this rule will be allowed to pass through."
      DEFVAL { deny }
      ::= { cLReapAclRuleEntry 2 }

cLReapAclRuleSourceIpAddressType OBJECT-TYPE
         SYNTAX      InetAddressType
         MAX-ACCESS  read-create
         STATUS      current
         DESCRIPTION
                "This object specifies source IP address type of 
		the ACL rule. The value is limited to ipv4 only."
         ::= { cLReapAclRuleEntry 3 }

cLReapAclRuleSourceIpAddress OBJECT-TYPE
         SYNTAX      InetAddress
         MAX-ACCESS  read-create
         STATUS      current
         DESCRIPTION
                "The object specifies source IP address of the ACL 
		rule. It cab be any ipv4 source address.
		A value 0 implies any sourse address."
         ::= { cLReapAclRuleEntry 4 }

cLReapAclRuleSourceIpNetmaskType OBJECT-TYPE
         SYNTAX      InetAddressType
         MAX-ACCESS  read-create
         STATUS      current
         DESCRIPTION
                "This object specifies source IP netmask type of 
		the ACL rule. The value is limited to ipv4 only."
         ::= { cLReapAclRuleEntry 5 }

cLReapAclRuleSourceIpNetmask OBJECT-TYPE
         SYNTAX      InetAddress
         MAX-ACCESS  read-create
         STATUS      current
         DESCRIPTION
                "This object specifies source IP netmask of the 
		ACL rule.  A value '0' implies any source mask."
         ::= { cLReapAclRuleEntry 6 }

cLReapAclRuleDestinationIpAddressType OBJECT-TYPE
         SYNTAX      InetAddressType
         MAX-ACCESS  read-create
         STATUS      current
         DESCRIPTION
                "This object specifies destination IP address type of 
		the ACL rule. The value is limited to ipv4 only."

         ::= { cLReapAclRuleEntry 7 }

cLReapAclRuleDestinationIpAddress OBJECT-TYPE
         SYNTAX      InetAddress
         MAX-ACCESS  read-create
         STATUS      current
         DESCRIPTION
                "The object specifies destination IP address of the ACL 
		rule. It cab be any ipv4 source address. A value '0'
                implies any destination address."
         ::= { cLReapAclRuleEntry 8 }


cLReapAclRuleDestinationIpNetmaskType OBJECT-TYPE
         SYNTAX      InetAddressType
         MAX-ACCESS  read-create
         STATUS      current
         DESCRIPTION
                "This object specifies destination IP netmask type of 
		the ACL rule. The value is limited to ipv4 only."
         ::= { cLReapAclRuleEntry 9 }

cLReapAclRuleDestinationIpNetmask OBJECT-TYPE
         SYNTAX      InetAddress
         MAX-ACCESS  read-create
         STATUS      current
         DESCRIPTION
                "This object specifies destination IP netmask of the 
		ACL rule. A value '0' implies any destination mask."
         ::= { cLReapAclRuleEntry 10 }

cLReapAclRuleProtocol OBJECT-TYPE
        SYNTAX Unsigned32(0..256)
        MAX-ACCESS read-create
        STATUS current
        DESCRIPTION
                "This object specifies protocol of the packet. 
		 It can be either of the pre specified protocols like
		 TCP, UDP, ICMP, ESP, AH, GRE, IP, Ethernet Over IP, 
		 OSPF or any number between 0 and 255. 
		 A value 256 implies that this rule applies
                 to 'Any' protocol."
        DEFVAL { 256 }
        ::= { cLReapAclRuleEntry 11 }

cLReapAclRuleStartSourcePort OBJECT-TYPE
        SYNTAX Unsigned32(0..65536)
        MAX-ACCESS read-create
        STATUS current
        DESCRIPTION
                "This object specifies source port of the packet. 
		 It can be either of the pre specified ports like HTTP,
		 HTTPS, Telnet, RADIUS etc or any number between 0 and
		 65535. A value 65536 implies that this rule applies 
		 to 'Any' source port. This value can be set only if 
		 the protocol is set to TCP or UDP.  Otherwise the 
		 value is set to Any(65536)."
        DEFVAL { 0 }
        ::= { cLReapAclRuleEntry 12 }

cLReapAclRuleEndSourcePort OBJECT-TYPE
        SYNTAX Unsigned32(0..65536)
        MAX-ACCESS read-create
        STATUS current
        DESCRIPTION
                "This object specifies source port of the packet. 
		 It can be either of the pre specified ports like HTTP,
		 HTTPS, Telnet, RADIUS etc or any number between 0 and
		 65535. A value 65536 implies that this rule applies 
		 to 'Any' source port. This value can be set only if 
		 the protocol is set to TCP or UDP.  Otherwise the 
		 value is set to Any(65536)."
        DEFVAL { 65535 }
        ::= { cLReapAclRuleEntry 13 }

cLReapAclRuleStartDestinationPort OBJECT-TYPE
        SYNTAX Unsigned32(0..65536)
        MAX-ACCESS read-create
        STATUS current
        DESCRIPTION
                "This object specifies destination port of the packet. 
		 It can be either of the pre specified ports like HTTP,
		 HTTPS, Telnet, RADIUS etc or any number between 0 and
		 65535. A value 65536 implies that this rule applies 
		 to 'Any' destination port. This value can be set only
		 if the protocol is set to TCP or UDP.  Otherwise the 
		 value is set to Any(65536)."
        DEFVAL { 0 }
        ::= { cLReapAclRuleEntry 14 }

cLReapAclRuleEndDestinationPort OBJECT-TYPE
        SYNTAX Unsigned32(0..65536)
        MAX-ACCESS read-create
        STATUS current
        DESCRIPTION
                "This object specifies destination port of the packet. 
		 It can be either of the pre specified ports like HTTP,
		 HTTPS, Telnet, RADIUS etc or any number between 0 and
		 65535. A value 65536 implies that this rule applies 
		 to 'Any' destination port. This value can be set only
		 if the protocol is set to TCP or UDP.  Otherwise the 
		 value is set to Any(65536)."
        DEFVAL { 65535 }
        ::= { cLReapAclRuleEntry 15 }

cLReapAclRuleDscp OBJECT-TYPE
        SYNTAX Unsigned32(0..256)
        MAX-ACCESS read-create
        STATUS current
        DESCRIPTION
                "This object specifies DSCP value of the rule. 
		A value 256 implies 'Any'."
        DEFVAL { 256 }
        ::= { cLReapAclRuleEntry 16 }

cLReapAclNewRuleIndex OBJECT-TYPE
      SYNTAX Unsigned32(1..64)
      MAX-ACCESS read-create
      STATUS     current
      DESCRIPTION
             "This object specifies new index of the ACL rule.
	      This attribute should be updated if the requirement is 
              to reset the sequence of the rules of an ACL. A read 
             on this will yield the same value as cLReapAclRuleIndex."
      ::= { cLReapAclRuleEntry 17 }

cLReapAclRuleRowStatus OBJECT-TYPE
      SYNTAX     RowStatus
      MAX-ACCESS read-create
      STATUS     current
      DESCRIPTION
             "This object specifies row status of the ACL rule."
      ::= { cLReapAclRuleEntry 18 }

-- *******************************************************************
-- cLReapIpv6AclTable
-- *******************************************************************

cLReapIpv6AclTable OBJECT-TYPE
    SYNTAX          SEQUENCE OF CLReapIpv6AclEntry 
    MAX-ACCESS      not-accessible
    STATUS          current
    DESCRIPTION
        "The table listing ACLs (Access Control Lists) on the
         device."
    ::= { ciscoLwappReapIpv6AclConfig 1 }

cLReapIpv6AclEntry OBJECT-TYPE
    SYNTAX          CLReapIpv6AclEntry
    MAX-ACCESS      not-accessible
    STATUS          current
    DESCRIPTION
        "Each entry in this table provides information about
         one ACL of the controller."
    INDEX           { cLReapIpv6AclName } 
    ::= { cLReapIpv6AclTable 1 }

CLReapIpv6AclEntry ::= SEQUENCE {
        cLReapIpv6AclName         SnmpAdminString,
        cLReapIpv6AclApplyMode    INTEGER,
        cLReapIpv6AclRowStatus    RowStatus
}

cLReapIpv6AclName OBJECT-TYPE
    SYNTAX          SnmpAdminString(SIZE  (1..32))
    MAX-ACCESS      not-accessible
    STATUS          current
    DESCRIPTION
        "This object represents name of the Access Control List." 
    ::= { cLReapIpv6AclEntry 1 }

cLReapIpv6AclApplyMode OBJECT-TYPE
    SYNTAX          INTEGER  {
                        notapplied(1),
                        applied(2)
                    }
    MAX-ACCESS      read-only
    STATUS          current
    DESCRIPTION
        "This object represents whether IPv6 ACL is applied or not. 
         A value of notapplied (1) indicates that, ACL has not been 
         applied on the device.
         A value of applied (2) indicates that, ACL has been applied 
         on the device." 
    ::= { cLReapIpv6AclEntry 2 }

cLReapIpv6AclRowStatus OBJECT-TYPE
    SYNTAX          RowStatus
    MAX-ACCESS      read-create
    STATUS          current
    DESCRIPTION
        "This is the status column for this row and is used to create
         and delete specific instance of row in this table."
    ::= { cLReapIpv6AclEntry 3 }
 

-- *******************************************************************
-- cLReapIpv6AclRuleTable
-- *******************************************************************

cLReapIpv6AclRuleTable OBJECT-TYPE
    SYNTAX          SEQUENCE OF CLReapIpv6AclRuleEntry 
    MAX-ACCESS      not-accessible
    STATUS          current
    DESCRIPTION
        "The table represents the ACL rules(Access Control List Entries)."
    ::= { ciscoLwappReapIpv6AclConfig 2 }

cLReapIpv6AclRuleEntry OBJECT-TYPE
    SYNTAX          CLReapIpv6AclRuleEntry
    MAX-ACCESS      not-accessible
    STATUS          current
    DESCRIPTION
        "Each entry in this table provides information about
         one ACL rule of the controller."
    INDEX           {
                        cLReapIpv6AclName,
                        cLReapIpv6AclRuleIndex
                    } 
    ::= { cLReapIpv6AclRuleTable 1 }

CLReapIpv6AclRuleEntry ::= SEQUENCE {
        cLReapIpv6AclRuleIndex                          Unsigned32,
        cLReapIpv6AclRuleAction                         INTEGER,
        cLReapIpv6AclRuleSourceAddressType              InetAddressType,
        cLReapIpv6AclRuleSourceAddress                  InetAddress,
        cLReapIpv6AclRuleSourcePrefixLength             InetAddressPrefixLength,
        cLReapIpv6AclRuleDestinationAddressType         InetAddressType,
        cLReapIpv6AclRuleDestinationAddress             InetAddress,
        cLReapIpv6AclRuleDestinationPrefixLength        InetAddressPrefixLength,
        cLReapIpv6AclRuleProtocol                       Unsigned32,
        cLReapIpv6AclRuleStartSourcePort                InetPortNumber,
        cLReapIpv6AclRuleEndSourcePort                  InetPortNumber,
        cLReapIpv6AclRuleStartDestinationPort           InetPortNumber,
        cLReapIpv6AclRuleEndDestinationPort             InetPortNumber,
        cLReapIpv6AclRuleDscp                           Unsigned32,
        cLReapIpv6AclNewRuleIndex                       Unsigned32,
        cLReapIpv6AclRuleRowStatus                      RowStatus
}

cLReapIpv6AclRuleIndex OBJECT-TYPE
    SYNTAX          Unsigned32 (1..64)
    MAX-ACCESS      not-accessible
    STATUS          current
    DESCRIPTION
        "This object represents a unique ACL rule. This can be
         updated by using cLReapIpv6AclNewRuleIndex to reset the sequence 
         of the rules of an ACL." 
    ::= { cLReapIpv6AclRuleEntry 1 }

cLReapIpv6AclRuleAction OBJECT-TYPE
    SYNTAX          INTEGER  {
                        deny(1),
                        permit(2)
                    }
    MAX-ACCESS      read-create
    STATUS          current
    DESCRIPTION
        "This object specifies the permission mode of a rule.
         A value of deny(1) indicates that, rule is to be 
         denied.
         A value of permit(2) indicates that, rule is to be 
         permit."
    DEFVAL          { deny } 
    ::= { cLReapIpv6AclRuleEntry 2 }

cLReapIpv6AclRuleSourceAddressType OBJECT-TYPE
    SYNTAX          InetAddressType
    MAX-ACCESS      read-create
    STATUS          current
    DESCRIPTION
        "This object specifies the type of the source IP address of the
        ACL rule." 
    ::= { cLReapIpv6AclRuleEntry 3 }

cLReapIpv6AclRuleSourceAddress OBJECT-TYPE
    SYNTAX          InetAddress
    MAX-ACCESS      read-create
    STATUS          current
    DESCRIPTION
        "This object specifies the source IP address." 
    ::= { cLReapIpv6AclRuleEntry 4 }

cLReapIpv6AclRuleSourcePrefixLength OBJECT-TYPE
    SYNTAX          InetAddressPrefixLength 
    MAX-ACCESS      read-create
    STATUS          current
    DESCRIPTION
        "This object specifies the prefix length for source
         IP address." 
    ::= { cLReapIpv6AclRuleEntry 5 }

cLReapIpv6AclRuleDestinationAddressType OBJECT-TYPE
    SYNTAX          InetAddressType
    MAX-ACCESS      read-create
    STATUS          current
    DESCRIPTION
        "This object specifies the type of the destination IP address."
    ::= { cLReapIpv6AclRuleEntry 6 }

cLReapIpv6AclRuleDestinationAddress OBJECT-TYPE
    SYNTAX          InetAddress
    MAX-ACCESS      read-create
    STATUS          current
    DESCRIPTION
        "This object specifies the destination IP address."
    ::= { cLReapIpv6AclRuleEntry 7 }

cLReapIpv6AclRuleDestinationPrefixLength OBJECT-TYPE
    SYNTAX          InetAddressPrefixLength 
    MAX-ACCESS      read-create
    STATUS          current
    DESCRIPTION
        "This object specifies the prefix length for destination
         IP address." 
    ::= { cLReapIpv6AclRuleEntry 8 }

cLReapIpv6AclRuleProtocol OBJECT-TYPE
    SYNTAX          Unsigned32 (0..256)
    MAX-ACCESS      read-create
    STATUS          current
    DESCRIPTION
        "This object specifies protocol of the packet. It can 
         be either of the pre specified protocols like TCP, UDP, 
         ICMP, ESP, AH, GRE,IP, ethernet over IP, OSPF or any 
         number between 0 and 255. A value 256 implies that this 
         rule applies to 'Any' protocol."
    DEFVAL          { 256 } 
    ::= { cLReapIpv6AclRuleEntry 9 }

cLReapIpv6AclRuleStartSourcePort OBJECT-TYPE
    SYNTAX          InetPortNumber
    MAX-ACCESS      read-create
    STATUS          current
    DESCRIPTION
        "This object specifies the start source port of the
         packet. It can be either of the pre specified ports 
         like HTTP, HTTPS, Telnet, RADIUS etc or any number 
         between 0 and 65535." 
    DEFVAL          { 0 } 
    ::= { cLReapIpv6AclRuleEntry 10 }

cLReapIpv6AclRuleEndSourcePort OBJECT-TYPE
    SYNTAX          InetPortNumber
    MAX-ACCESS      read-create
    STATUS          current
    DESCRIPTION
        "This object specifies the end Source Port of the packet.
         It can be either of the pre specified ports like HTTP, 
         HTTPS, Telnet, RADIUS etc or any number between 0 and 
         65535."
    DEFVAL          { 65535 } 
    ::= { cLReapIpv6AclRuleEntry 11 }

cLReapIpv6AclRuleStartDestinationPort OBJECT-TYPE
    SYNTAX          InetPortNumber
    MAX-ACCESS      read-create
    STATUS          current
    DESCRIPTION
        "This object specifies the start Destination Port of the
         packet. It can be either of the pre specified ports like HTTP,
         HTTPS, Telnet, RADIUS etc or any number between 0 and 65535."
    DEFVAL          { 0 } 
    ::= { cLReapIpv6AclRuleEntry 12 }

cLReapIpv6AclRuleEndDestinationPort OBJECT-TYPE
    SYNTAX          InetPortNumber
    MAX-ACCESS      read-create
    STATUS          current
    DESCRIPTION
        "This object specifies the End Destination Port of the packet.
         It can be either of the pre specified ports like HTTP, HTTPS,
         Telnet, RADIUS etc or any number between 0 and 65535."
    DEFVAL          { 65535 } 
    ::= { cLReapIpv6AclRuleEntry 13 }

cLReapIpv6AclRuleDscp OBJECT-TYPE
    SYNTAX          Unsigned32 (0..256)
    MAX-ACCESS      read-create
    STATUS          current
    DESCRIPTION
        "This object specifies the DSCP value of the rule.
         A value 256 implies Any."
    DEFVAL          { 256 } 
    ::= { cLReapIpv6AclRuleEntry 14 }

cLReapIpv6AclNewRuleIndex OBJECT-TYPE
    SYNTAX          Unsigned32 (1..64)
    MAX-ACCESS      read-create
    STATUS          current
    DESCRIPTION
        "This object specifies the new Index of the ACL rule. This
         object should be updated if the requirement is to reset the
         sequence of the rules of an ACL." 
    ::= { cLReapIpv6AclRuleEntry 15 }

cLReapIpv6AclRuleRowStatus OBJECT-TYPE
    SYNTAX          RowStatus
    MAX-ACCESS      read-create
    STATUS          current
    DESCRIPTION
        "This is the status column for this row and is used to create
        and delete specific instances of rows in this table." 
    ::= { cLReapIpv6AclRuleEntry 16 }

-- *******************************************************************
-- cLReapIpv6AclUrlDomainRuleTable
-- *******************************************************************
cLReapIpv6AclUrlDomainRuleTable OBJECT-TYPE
      SYNTAX      SEQUENCE OF CLReapIpv6AclUrlDomainRuleEntry
      MAX-ACCESS  not-accessible
      STATUS      current
      DESCRIPTION
            "This table represents url domain ACL Rules(url based Access 
            Control List entries) on the ACL with name cLReapIpv6AclName."
      ::= { ciscoLwappReapIpv6AclConfig 3 }

cLReapIpv6AclUrlDomainRuleEntry OBJECT-TYPE
      SYNTAX      CLReapIpv6AclUrlDomainRuleEntry 
      MAX-ACCESS  not-accessible
      STATUS      current
      DESCRIPTION
            "Each Entry represents the attributes for cLReapIpv6AclUrlDomainRuleTable.
             An Url Domain rule entry gets added to the table on creating 
             a rule on flexconnect ACL."
      INDEX           {
                        cLReapIpv6AclName,
                        cLReapIpv6AclUrlDomainRuleIndex
                    }
      ::= { cLReapIpv6AclUrlDomainRuleTable 1 }

CLReapIpv6AclUrlDomainRuleEntry::= SEQUENCE {
                    cLReapIpv6AclUrlDomainRuleIndex        Unsigned32,
                    cLReapIpv6AclUrlDomainRuleUrl          SnmpAdminString,
                    cLReapIpv6AclUrlDomainRuleAction       INTEGER,
                    cLReapIpv6AclUrlDomainRuleRowStatus    RowStatus
            }

cLReapIpv6AclUrlDomainRuleIndex OBJECT-TYPE
      SYNTAX     Unsigned32(1..20)
      MAX-ACCESS read-create
      STATUS     current
      DESCRIPTION
             "This object specifies the index of the Url domain Ipv6 ACL rule. 
              It can be used to reset the sequence of the Url rules of an ACL."
      ::= { cLReapIpv6AclUrlDomainRuleEntry 1 }

cLReapIpv6AclUrlDomainRuleUrl OBJECT-TYPE
      SYNTAX     SnmpAdminString
      MAX-ACCESS read-write
      STATUS     current
      DESCRIPTION
             "This object specifies the URL name for the url domain rule."
      ::= { cLReapIpv6AclUrlDomainRuleEntry 2 }

cLReapIpv6AclUrlDomainRuleAction OBJECT-TYPE
    SYNTAX INTEGER  {
                        deny(1),
                        permit(2)
                    }
      MAX-ACCESS read-write
      STATUS     current
      DESCRIPTION
             "This object specifies the permission mode of url domain rule.
	     A value of 'deny(1)' specifies client traffic matches
	     this rule will be blocked.
	     A value of 'permit(2)' specifies client traffic matches
	     this rule will be allowed to pass through."
      DEFVAL { deny }
      ::= { cLReapIpv6AclUrlDomainRuleEntry 3 }

cLReapIpv6AclUrlDomainRuleRowStatus OBJECT-TYPE
      SYNTAX     RowStatus
      MAX-ACCESS read-create
      STATUS     current
      DESCRIPTION
             "This is the status column for this row and is used to
              create and delete specific instances of rows in this table."
      ::= { cLReapIpv6AclUrlDomainRuleEntry 4 }

-- *******************************************************************
-- ciscoLwappReapGlobalConfig
-- *******************************************************************

cLReapArpCaheEnabled OBJECT-TYPE
      SYNTAX     TruthValue
      MAX-ACCESS read-write
      STATUS     current
      DESCRIPTION
            "This object specifies whether ARP cache feature is enabled
             for the flexconnect Access Points connected to the 
             Wireless LAN Controller."
      ::= { ciscoLwappReapGlobalConfig 1 }

-- ********************************************************************
-- *    Compliance statements
-- ********************************************************************

ciscoLwappReapMIBCompliances  OBJECT IDENTIFIER
    ::= { ciscoLwappReapMIBConform 1 }

ciscoLwappReapMIBGroups  OBJECT IDENTIFIER
    ::= { ciscoLwappReapMIBConform 2 }

ciscoLwappReapMIBCompliance MODULE-COMPLIANCE
        STATUS     deprecated 
        DESCRIPTION
                "The compliance statement for the SNMP entities that
                implement the ciscoLwappReapMIB module. "
        MODULE MANDATORY-GROUPS {                
                ciscoLwappReapWlanConfigGroup,
                ciscoLwappReapApConfigGroup
             }

        ::= { ciscoLwappReapMIBCompliances 1 }

ciscoLwappReapMIBComplianceRev1 MODULE-COMPLIANCE
        STATUS     deprecated 
        DESCRIPTION
                "The compliance statement for the SNMP entities that
                implement the ciscoLwappReapMIB module. "
        MODULE MANDATORY-GROUPS {                
                ciscoLwappReapWlanConfigGroup,
                ciscoLwappReapApConfigGroup,
                ciscoLwappReapGroupConfigGroup
             }

        ::= { ciscoLwappReapMIBCompliances 2 }

ciscoLwappReapMIBComplianceRev2 MODULE-COMPLIANCE
    STATUS          deprecated
    DESCRIPTION
        "The compliance statement for the SNMP entities that
        implement the ciscoLwappReapMIB module."
    MODULE          -- this module
    MANDATORY-GROUPS {
                        ciscoLwappReapWlanConfigGroup,
                        ciscoLwappReapApConfigGroup,
                        ciscoLwappReapGroupConfigGroup
                    }
    ::= { ciscoLwappReapMIBCompliances 3 }

ciscoLwappReapMIBComplianceRev3 MODULE-COMPLIANCE
    STATUS          deprecated
    DESCRIPTION
        "The compliance statement for the SNMP entities that
        implement the ciscoLwappReapMIB module."
    MODULE          -- this module
    MANDATORY-GROUPS {
                        ciscoLwappReapWlanConfigGroup,
                        ciscoLwappReapApConfigGroup,
                        ciscoLwappReapGroupConfigGroup,
                        ciscoLwappReapGroupConfigRadiusGroup,
                        ciscoLwappReapGroupConfigUserAuthGroup,
                        ciscoLwappReapApConfigGroupHomeAp
                    }
    ::= { ciscoLwappReapMIBCompliances 4 }

ciscoLwappReapMIBComplianceRev4 MODULE-COMPLIANCE
    STATUS          deprecated
    DESCRIPTION
        "The compliance statement for the SNMP entities that
        implement the ciscoLwappReapMIB module."
    MODULE          -- this module
    MANDATORY-GROUPS {
                        ciscoLwappReapWlanConfigGroup,
                        ciscoLwappReapApConfigGroup,
                        ciscoLwappReapGroupConfigGroup,
                        ciscoLwappReapGroupConfigUserAuthGroup,
                        ciscoLwappReapApConfigGroupHomeAp,
                        ciscoLwappReapGroupConfigRadiusGroup1
                    }
    ::= { ciscoLwappReapMIBCompliances 5 }

ciscoLwappReapMIBComplianceRev5 MODULE-COMPLIANCE
    STATUS          deprecated
    DESCRIPTION
        "The compliance statement for the SNMP entities that
        implement the ciscoLwappReapMIB module."
    MODULE          -- this module
    MANDATORY-GROUPS {
                        ciscoLwappReapWlanConfigGroup,
                        ciscoLwappReapApConfigGroup,
                        ciscoLwappReapGroupConfigGroup,
                        ciscoLwappReapGroupConfigUserAuthGroup,
                        ciscoLwappReapApConfigGroupHomeAp,
                        ciscoLwappReapGroupConfigRadiusGroup1,
                        ciscoLwappReapWlanConfigGroupSup1
                    }
    ::= { ciscoLwappReapMIBCompliances 6 }
    
ciscoLwappReapMIBComplianceRev6 MODULE-COMPLIANCE
    STATUS          deprecated 
    DESCRIPTION
        "The compliance statement for the SNMP entities that
        implement the ciscoLwappReapMIB module."
    MODULE          -- this module
    MANDATORY-GROUPS {
                        ciscoLwappReapWlanConfigGroup,
                        ciscoLwappReapApConfigGroup,
                        ciscoLwappReapGroupConfigGroup,
                        ciscoLwappReapGroupConfigUserAuthGroup,
                        ciscoLwappReapApConfigGroupHomeAp,
                        ciscoLwappReapGroupConfigRadiusGroup1,
                        ciscoLwappReapWlanConfigGroupSup1,
                        ciscoLwappReapAclConfigGroup
                    }
    ::= { ciscoLwappReapMIBCompliances 7 }

ciscoLwappReapMIBComplianceRev7 MODULE-COMPLIANCE
    STATUS          current 
    DESCRIPTION
        "The compliance statement for the SNMP entities that
        implement the ciscoLwappReapMIB module."
    MODULE          -- this module
    MANDATORY-GROUPS {
                        ciscoLwappReapWlanConfigGroup,
                        ciscoLwappReapApConfigGroup,
                        ciscoLwappReapGroupConfigGroup,
                        ciscoLwappReapGroupConfigUserAuthGroup,
                        ciscoLwappReapApConfigGroupHomeAp,
                        ciscoLwappReapGroupConfigRadiusGroup1,
                        ciscoLwappReapWlanConfigGroupSup1,
                        ciscoLwappReapAclConfigGroupRev1,
                        ciscoLwappReapIpv6AclConfigGroup
                    }
    ::= { ciscoLwappReapMIBCompliances 8 }

-- ********************************************************************
-- *    Units of conformance
-- ********************************************************************

ciscoLwappReapWlanConfigGroup OBJECT-GROUP
    OBJECTS { 
    		cLReapWlanEnLocalSwitching,
    		cLReapWlanVlanCentralSwitching, 
        	cLReapWlanDhcpCentral, 
        	cLReapWlanDhcpOverrideDNS,
			cLReapWlanNatPatEnabled,
       		cLReapWlanAssocCentral,
            cLReapWlanPostAuthIpv4Acl,
            cLReapWlanPostAuthIpv6Acl

    	}
    STATUS          current
    DESCRIPTION
        "This collection of objects represent the WLAN
        configuration to be passed to the REAP."
    ::= { ciscoLwappReapMIBGroups 1 }

ciscoLwappReapApConfigGroup OBJECT-GROUP
    OBJECTS         {
                        cLReapApNativeVlanId,
                        cLReapApVlanId,
                        cLReapApVlanEnable,
                        cLReapInstallMappingRadioBackhaul,
        		cLReapApResilientMode,
      			cLReapApNativeVlanLevel,
      			cLReapApVlanInheritance,
        		cLReapApVlanRowStatus,
        		cLReapApVlanUsedBySecEthInterface,
        		cLReapIngressAcl, 
                   	cLReapEgressAcl, 
                   	cLReapApVlanIdAclRowStatus, 
                   	cLReapVlanIdAclType,
                   	cLReapApWebAuthAcl,
                	cLReapApWebAuthAclRowStatus,
                	cLReapWebPolicyAclRowStatus,
                	cLReapApLocalSplitAcl,
                	cLReapApLocalSplitAclRowStatus,
                	cLReapApDhcpCentral,
                	cLReapApDhcpOverrideDNS,
                	cLReapApNatPatEnabled,
                	cLReapApDhcpRowStatus,
                	cLReapApInheritance,
                	cLReapApL2Acl,
                	cLReapApL2AclRowStatus,
                	cLReapArpCaheEnabled
                        
                    }
    STATUS          current
    DESCRIPTION
        "This collection of objects represent the information
        needed by the REAP AP to locally switch the client
        data packets.  The collection also includes the
        VLAN configuration on the REAP."
    ::= { ciscoLwappReapMIBGroups 2 }

ciscoLwappReapGroupConfigGroup OBJECT-GROUP
    OBJECTS         {
                        cLReapGroupPrimaryRadiusIndex,
                        cLReapGroupSecondaryRadiusIndex,
                        cLReapGroupStorageType,
                        cLReapGroupRowStatus,
                        cLReapGroupApStorageType,
                        cLReapGroupApRowStatus,
                        cLReapGroupApPnPConflict,
                        cLReapGroupEfficientApUpgradeEnable,
        		cLReapGroupApUpgradeStart,
        		cLReapGroupSlaveMaxRetryCount,
    			cLReapGroupPrimaryRadiusServerType,
        		cLReapGroupPrimaryRadiusServerAddress,
        		cLReapGroupPrimaryRadiusServerPort,
        		cLReapGroupPrimaryServerSecret, 
        		cLReapGroupSecRadiusServerType,
        		cLReapGroupSecRadiusServerAddress,
        		cLReapGroupSecRadiusServerPort,
        		cLReapGroupSecServerSecret,
        		cLReapGroupRadiusPeapEnable,
        		cLReapGroupRadiusEapTlsEnable,
        		cLReapGroupCertificateEapTlsEnable,
        		cLReapGroupNativeVlanId,
        		cLReapGroupVlanEnable,
        		cLReapGroupOverrideVlanEnable,
        		cLReapGroupHttpProxyIpType,
        		cLReapGroupHttpProxyIp,
        		cLReapGroupHttpProxyPort,
        		cLReapGroupVlanTemplateName,
        		cLReapGroupApEntryType,
        		cLReapGroupIngressAcl,
                   	cLReapGroupEgressAcl,
                   	cLReapGroupVlanAclRowStatus,
                   	cLReapGroupVlanOrder,
                   	cLReapGroupWebAuthAcl,
                   	cLReapGroupAclRowStatus,
                        cLReapGroupWebAuthIpv6Acl,
                   	cLReapGroupWebPolicyAclRowStatus,
                        cLReapGroupWebPolicyAclType,
                   	cLReapGroupLocalSplitAcl,
                   	cLReapGroupLocalSplitAclRowStatus,
                   	cLReapGroupDhcpCentral,
                	cLReapGroupDhcpOverrideDNS,
                	cLReapGroupNatPatEnabled,
                	cLReapGroupDhcpRowStatus,
                	cLReapGroupWlanVlanId,
                	cLReapGroupVlanRowStatus,
                	cLReapGroupAVCFlexProfileName,
            		cLReapGroupNbarStatsVisibilityEnable, 
            		cLReapGroupAVCFlexRowStatus,
            		cLReapMasterApModel,
                	cLReapMasterApManual,
                	cLReapMasterApRowStatus,
                	cLReapL2AclApplyMode,
                	cLReapL2AclRowStatus,
                	cLReapL2AclRuleAction,
                    	cLReapL2AclRuleEthertype,
                    	cLReapL2AclRuleEthertypeMask,
                    	cLReapL2AclRuleDirection,
                    	cLReapL2AclNewRuleIndex,
                    	cLReapL2AclRuleRowStatus,
                    	cLReapGroupPrimaryRadiusIndex,
                    	cLReapGroupSecondaryRadiusIndex,
                    	cLReapGroupStorageType,
                    	cLReapGroupEfficientApUpgradeEnable,
                    	cLReapGroupApUpgradeStart,
			cLReapGroupEfficientApJoinEnable,	
        			cLReapGroupAutoApTypeConversion
                   		  
                    }
    STATUS          current
    DESCRIPTION
        "This collection of objects represent the information
        needed by the REAP APs to configure REAP groups."
    ::= { ciscoLwappReapMIBGroups 3 }
ciscoLwappReapGroupConfigRadiusGroup OBJECT-GROUP
        OBJECTS {
                 cLReapGroupRadiusPacTimeout,
                 cLReapGroupRadiusAuthorityId,
                 cLReapGroupRadiusAuthorityInfo,
                 cLReapGroupRadiusServerKey,
                 cLReapGroupRadiusIgnoreKey,
                 cLReapGroupRadiusEnable,
                 cLReapGroupRadiusLeapEnable,
                 cLReapGroupRadiusEapFastEnable
        }
        STATUS     deprecated
        DESCRIPTION
                "This collection of objects represent the RADIUS
                information needed by the REAP APs in a REAP group."
        ::= { ciscoLwappReapMIBGroups 4 }

ciscoLwappReapGroupConfigUserAuthGroup OBJECT-GROUP
    OBJECTS         {
                        cLReapGroupUserPassword,
                        cLReapGroupUserStorageType,
                        cLReapGroupUserRowStatus
                    }
    STATUS          current
    DESCRIPTION
        "This collection of objects represent the information
        needed for user authentication."
    ::= { ciscoLwappReapMIBGroups 5 }

ciscoLwappReapApConfigGroupHomeAp OBJECT-GROUP
    OBJECTS         {
                        cLReapHomeApEnable,
                        cLReapApLeastLatencyJoinEnable,
                        cLReapWlanClientIpLearnEnable,
                        cLReapHomeApLocalSsidReset
                    }
    STATUS          current
    DESCRIPTION
        "This supplemental collection of objects represents
        objects related to Home AP configuration for 
        REAP AP."
    ::= { ciscoLwappReapMIBGroups 6 }

ciscoLwappReapGroupConfigRadiusGroup1 OBJECT-GROUP
    OBJECTS         {
                        cLReapGroupRadiusAuthorityId,
                        cLReapGroupRadiusAuthorityInfo,
                        cLReapGroupRadiusServerKey,
                        cLReapGroupRadiusIgnoreKey,
                        cLReapGroupRadiusEnable,
                        cLReapGroupRadiusLeapEnable,
                        cLReapGroupRadiusEapFastEnable,
                        cLReapGroupRadiusPacTimeoutCtrl
                    }
    STATUS          current
    DESCRIPTION
        "This collection of objects represent the RADIUS
        information needed by the REAP APs in a REAP group."
    ::= { ciscoLwappReapMIBGroups 7 }

ciscoLwappReapWlanConfigGroupSup1 OBJECT-GROUP
    OBJECTS         { cLReapWlanApAuth }
    STATUS          current
    DESCRIPTION
        "This collection of objects represent additional WLAN
        configuration to be passed to the REAP."
    ::= { ciscoLwappReapMIBGroups 8 }
    
ciscoLwappReapAclConfigGroup OBJECT-GROUP
    OBJECTS         {
                        cLReapAclName,
                	cLReapAclApplyMode,
                	cLReapAclRowStatus,
                	cLReapAclRuleIndex,
                    	cLReapAclRuleAction,
                    	cLReapAclRuleSourceIpAddressType,
                   	cLReapAclRuleSourceIpAddress,
                    	cLReapAclRuleSourceIpNetmaskType,
                    	cLReapAclRuleSourceIpNetmask,
                    	cLReapAclRuleDestinationIpAddressType,
                    	cLReapAclRuleDestinationIpAddress,
                    	cLReapAclRuleDestinationIpNetmaskType,
                    	cLReapAclRuleDestinationIpNetmask,
                    	cLReapAclRuleProtocol,
                    	cLReapAclRuleStartSourcePort,
                    	cLReapAclRuleEndSourcePort,
                    	cLReapAclRuleStartDestinationPort,
                    	cLReapAclRuleEndDestinationPort,
                    	cLReapAclRuleDscp,
                    	cLReapAclNewRuleIndex,
                    	cLReapAclRuleRowStatus
                    }
    STATUS          deprecated 
    DESCRIPTION
        "This collection of objects represent the information
        needed for flexconnect ACLs."
    ::= { ciscoLwappReapMIBGroups 9 }

ciscoLwappReapAclConfigGroupRev1 OBJECT-GROUP
    OBJECTS         {
                        cLReapAclName,
                	cLReapAclApplyMode,
                	cLReapAclRowStatus,
                	cLReapAclRuleIndex,
                    	cLReapAclRuleAction,
                    	cLReapAclRuleSourceIpAddressType,
                   	cLReapAclRuleSourceIpAddress,
                    	cLReapAclRuleSourceIpNetmaskType,
                    	cLReapAclRuleSourceIpNetmask,
                    	cLReapAclRuleDestinationIpAddressType,
                    	cLReapAclRuleDestinationIpAddress,
                    	cLReapAclRuleDestinationIpNetmaskType,
                    	cLReapAclRuleDestinationIpNetmask,
                    	cLReapAclRuleProtocol,
                    	cLReapAclRuleStartSourcePort,
                    	cLReapAclRuleEndSourcePort,
                    	cLReapAclRuleStartDestinationPort,
                    	cLReapAclRuleEndDestinationPort,
                    	cLReapAclRuleDscp,
                    	cLReapAclNewRuleIndex,
                    	cLReapAclRuleRowStatus,
		    	cLReapAclUrlDomainRuleIndex,
                    	cLReapAclUrlDomainRuleUrl,
                    	cLReapAclUrlDomainRuleAction,
                    	cLReapAclUrlDomainRuleRowStatus
                    }
    STATUS          current
    DESCRIPTION
        "This collection of objects represent the information
        needed for flexconnect ACLs."
    ::= { ciscoLwappReapMIBGroups 10}

ciscoLwappReapIpv6AclConfigGroup OBJECT-GROUP
    OBJECTS         {
                        cLReapIpv6AclName,
                	cLReapIpv6AclApplyMode,
                	cLReapIpv6AclRowStatus,
                	cLReapIpv6AclRuleIndex,
                    	cLReapIpv6AclRuleAction,
			cLReapIpv6AclRuleSourceAddressType,
		        cLReapIpv6AclRuleSourceAddress,
        		cLReapIpv6AclRuleSourcePrefixLength,
        		cLReapIpv6AclRuleDestinationAddressType,
       			cLReapIpv6AclRuleDestinationAddress,
        		cLReapIpv6AclRuleDestinationPrefixLength,
        		cLReapIpv6AclRuleProtocol,
        		cLReapIpv6AclRuleStartSourcePort,
        		cLReapIpv6AclRuleEndSourcePort,
        		cLReapIpv6AclRuleStartDestinationPort,
        		cLReapIpv6AclRuleEndDestinationPort,
        		cLReapIpv6AclRuleDscp,
        		cLReapIpv6AclNewRuleIndex,
        		cLReapIpv6AclRuleRowStatus,
		    	cLReapIpv6AclUrlDomainRuleIndex,
                    	cLReapIpv6AclUrlDomainRuleUrl,
                    	cLReapIpv6AclUrlDomainRuleAction,
                    	cLReapIpv6AclUrlDomainRuleRowStatus
                    }
    STATUS          current
    DESCRIPTION
        "This collection of objects represent the information
        needed for flexconnect ACLs."
    ::= { ciscoLwappReapMIBGroups 11}

END


--%DNP%  MLC -Compiled MLC

--%DNP%  MTF -TRUE MTF
